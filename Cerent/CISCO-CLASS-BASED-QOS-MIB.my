-- *****************************************************************
-- Cisco Class-Based QoS Configuration and Statistics MIB
--
-- Copyright (c) 2000-2002, 2003 by Cisco Systems, Inc.
-- All rights reserved.
--
-- *****************************************************************


CISCO-CLASS-BASED-QOS-MIB DEFINITIONS ::= BEGIN

IMPORTS
        MODULE-IDENTITY,
        OBJECT-TYPE,
        Integer32,
        Counter32,
        Gauge32,
        Unsigned32,
        Counter64
                FROM SNMPv2-SMI

        Unsigned64,
        EntPhysicalIndexOrZero
                FROM CISCO-TC

        MODULE-COMPLIANCE,
        OBJECT-GROUP
                FROM SNMPv2-CONF

        TEXTUAL-CONVENTION,
        DisplayString,
        TruthValue
                FROM SNMPv2-TC

        ifIndex,
        InterfaceIndex
                FROM IF-MIB

        DlciNumber
                FROM CISCO-FRAME-RELAY-MIB
        
        ciscoMgmt
                FROM CISCO-SMI;

ciscoCBQosMIB MODULE-IDENTITY
        LAST-UPDATED    "200306090000Z"
        ORGANIZATION    "Cisco Systems, Inc."
        CONTACT-INFO
                "       Cisco Systems
                        Customer Service

                Postal: 170 W. Tasman Drive
                        San Jose, CA  95134-1706
                        USA

                   Tel: +1 800 553-NETS

                E-mail: cs-qos@cisco.com"

        DESCRIPTION
           "        Cisco Class-Based QoS MIB

                **********************************
                            Overview
                **********************************
           This MIB provides read access to Quality of Service (QoS) 
           configuration and statistics information for Cisco 
           platforms that support the Modular Quality of Service 
           Command-line Interface (Modular QoS CLI).  We recommend 
           users of this MIB to review the user documentation of 
           MQC based QoS features.

           Configuration information available through this MIB includes
           all ClassMap, PolicyMap, Match Statements, and Feature 
           Actions configuration parameters. The definitions of each
           objects mentioned above are explained in the QoS objects
           section.

           Statistics available through this MIB include summary
           counts/rates by traffic class before and after any configured
           QoS policies are enforced.  In addition, detailed
           feature-specific statistics are available for select
           PolicyMap features.

           Contact your Cisco representative to determine on which
           platforms the MIB is currently supported.

                **********************************
                           QoS  Acronyms
                **********************************
           CIR : Committed Information Rate
           DSCP: Differentiated Service Code Point
           ECN : Explicite Congestion Notification
           IPHC: Internet Protocol Header Compression 
           PIR : Peak Information Rate
           PREC: Precedence
           QoS : Quality Of Services
           RED : Random Early Detect
           WRED: Weighted Random Early Detect
           
                **********************************
                            MIB Tables
                **********************************
           This MIB consists of the following tables:
             1 :  cbQosServicePolicy
             2 :  cbQosInterfacePolicy
             3 :  cbQosFrameRelayVCPolicy
             4 :  cbQosATMPVCPolicy
             5 :  cbQosObjects
             6 :  cbQosPolicyMapCfg
             7 :  cbQosClassMapCfg
             8 :  cbQosMatchStmtCfg
             9 :  cbQosQueueingCfg
             10:  cbQosREDCfg
             11:  cbQosREDClassCfg
             12:  cbQosPoliceCfg
             13:  cbQosTSCfg
             14:  cbQosSetCfg
             15:  cbQosClassMapStats
             16:  cbQosMatchStmtStats
             17:  cbQosPoliceStats
             18:  cbQosQueueingStats
             19:  cbQosTSStats
             20:  cbQosREDClassStats
             21:  cbQosPoliceActionCfg
             22:  cbQosIPHCCfg
             23:  cbQosIPHCStats

                **********************************
                          Definitions
                **********************************
           A logical interface in the context of this MIB is either
           a main-interface, a sub-interface, a Frame Relay DLCI,
           an ATM virtual circuit or the control-plane on the router.

           The (aggregate) control-plane on the router is defined as 
           a collection of processes running at process level on the
           platform (route) processor. This includes the functions 
           related to networking control capabilities such as routing,
           signaling, provisioning, as well as resource and service 
           discovery. Also includes process switched traffic on the
           device. 

           The term distributed control plane, in the context of 
           this mib, represents the control-plane functionality at
           the level of individual linecards. This is only
           applicable for the case of distributed platforms.

                **********************************
                           QoS Objects
                **********************************
           To understand Class-Based QoS features and how to navigate 
           the MIB tables above, the key element is to comprehend the 
           relationships among the different QoS objects. QoS objects 
           consist of ClassMaps, Match Statements and PolicyMaps, 
           and each Feature Actions. 

           Match Statement - The specific match criteria to identify
           packets for classification purposes.

           ClassMap - A user-defined traffic class that contains
           one or many match statements used to classify packets into
           different categories.

           Feature Action - An action is a QoS feature. Features 
           include police, traffic-shaping, queueing, random detect 
           and packet marking(set). After the traffic is being 
           classified, based on the traffic classification, we can 
           apply these action to each traffic class.

           PolicyMap - A user-defined policy that associates each QoS 
           action to the user-defined traffic class (ClassMap).

           Service Policy - Service policy is a policymap
           that is being attached to a logical interface. Because a
           policymap can also be a part of the hierarchical structure 
           (inside a classmap), only a policymap that is directly 
           attached to a logical interface is considered a service 
           policy.  Each service policy is uniquely identified by an 
           index called cbQosPolicyIndex. This number is usually 
           identical to its cbQosObjectsIndex as a policymap.

                *****************************************
                Runtime Instance vs Configuration objects
                *****************************************

           Each QoS objects have 2 sets of behaviours : 
           1: A configuration instance
                - Each QoS objects has it's configuration portion of
                  information attached to it. This information does
                  not change whether this object is attached on multiple
                  logical interfaces and used multiple times. We
                  uniquely identify each QoS object with identical
                  configuration with the same index - cbQosConfigIndex.
                  This index is used in all configuration related
                  tables. 

           2: A runtime instance
                - Each QoS objects has it's statistical portion of
                  information attached to it. This information changes
                  when this object is attached on multiple logical 
                  interfaces and used in various different places. We
                  uniquely identify each QoS runtime object instance 
                  with an index that is unique across multiple 
                  instances of the identical object - cbQosObjectsIndex.
                  This index is used in all statistical related tables. 

            In summary, a QoS object has 2 indexes associated with it:
            cbQosConfigIndex is used to identify it's configuration, 
            which does not change regardless of number of times and
            where it is being used; and cbQosObjectsIndex is used 
            to identify it's runtime statistics, depending on which
            logical interface and where in a given PolicyMap hierarchy
            this object is used, it may have multiple unique 
            identifiers to distinguish each unique usage (instance) of
            the same object.

                **********************************
                            Navigation
                **********************************
           The recommended method of navigating through all of the MIB 
           tables is to start by learning the cbQosServicePolicyTable 
           and cbQosObjectsTable MIB tables. In particular, Cisco 
           Systems recommends understanding the cbQosObjectsIndex and 
           cbQosParentObjectsIndex of each QoS feature.

           The cbQosPolicyIndex and cbQosObjectsIndex are 
           system-assigned numbers that identify each unique instance 
           of a QoS feature. These indexes are never reused between 
           router reboots, even when changes are made to the QoS 
           configuration. The cbQosPolicyIndex is designed to identify 
           the service policies attached to logical interfaces, while 
           the cbQosObjectsIndex is designed to identify each QoS 
           feature on a specified device.

           The cbQosParentObjectsIndex is designed to show the 
           hierarchical relationship of each QoS feature. 

                **********************************
                        cbQosServicePolicyTable
                **********************************
           Accessing cbQosServicePolicyTable requires 
           cbQosPolicyIndex. This index is a system-assigned number 
           to uniquely identify each service policy hanging off of
           each logical interface. Given cbQosPolicyIndex the tables
           provide the type of logical interface/media type on which
           this policy is applied, the direction in which this policy
           is enforced, and the SNMP interface index and/or the entity
           index of the underlying interface/entity. In the case of a
           policy being applied on a Frame Relay DLCI, the cbQosFrDLCI
           gives you the Frame Relay DLCI number to which this policy
           is attached. In the case of policy being attached to an ATM
           VC, cbQosAtmVPI and cbQosAtmVCI display the VPI and VCI of 
           the ATM interface respectively.

                **********************************
                        cbQosObjectsTable
                **********************************
           Accessing cbQosObjectsTable requires two indexes, 
           cbQosPolicyIndex and cbQosObjectsIndex. 

           Given a particular service policy on a given logical 
           interface, there could be PolicyMaps, ClassMaps, Match 
           Statements and Feature Actions being used. Each instance 
           of these objects is uniquely identified by
           cbQosObjectsIndex.

           Users need to decide which QoS object is interesting 
           and use the cbQosPolicyIndex and cbQosObjectsIndex to
           locate the right element of interest. This tables provides 
           cbQosObjectsType, cbQosConfigIndex, and 
           cbQosParentObjectsIndex. 

           To understand the relationship of cbQosObjectsIndex, 
           cbQosParentObjectsIndex and the hierarchical relationship 
           of the QoS objects, consider the following QoS 
           configuration example:

             Interface ethernet 0/1
                Input Service Policy cntlWebTraffic
                        ClassMap http
                                match ip http
                                set ip precedence 5

                Output Service Policy cntlSNMP_Telnet
                        ClassMap snmp
                                match ip snmp
                                shape average 8000 32 32
                        ClassMap Telnet
                                match ip telnet
                                shape average 10000 32 32

             Interface ethernet 0/2
                Input Service Policy cntlWebTraffic
                        ClassMap http
                                match ip http
                                set ip precedence 5

                Output Service Policy cntlSNMP_Telnet
                        ClassMap snmp
                                match ip snmp
                                shape average 8000 32 32
                        ClassMap Telnet
                                match ip telnet
                                shape average 10000 32 32

             *** In Ethernet 0/1 ***
             Assume the router assigned a cbQosConfigIndex=1024 and 
             cbQosObjectsIndex=1084 to Policy cntlWebTraffic. 
             Because it is attached to an interface, it has no parent 
             QoS object, and thus cbQosParentObjectsIndex=0. 
             In addition, because cntlWebTraffic is also the service 
             policy of the interface, it has a unique cbQosPolicyIndex 
             assigned to it. In most cases, it would be the same as 
             the cbQosObjectsIndex, which is 1084 in this case. 
             Therefore, the indexes are:
             cbQosPolicyIndex = 1084
             cbQosObjectsIndex = 1084
             cbQosConfigIndex = 1024

             Assuming the router assigned a cbQosObjectsIndex=1085 
             and cbQosConfigIndex=1025 to ClassMap http, it is 
             directly being used by Policy cntlWebTraffic, and therefore
             the cbQosParentObjectsIndex of ClassMap http will be 1084. 

             Assuming the router assigned a cbQosConfigIndex=1026 and
             cbQosObjectsIndex=1086 to match ip http, it is directly 
             used by ClassMap http, therefore the 
             cbQosParentObjectsIndex of match ip http will be 1085.

             Assuming the router assigned a cbQosConfigIndex=1027 and
             cbQosObjectsIndex=1087 to set ip precedence 5, it is 
             directly used by ClassMap http, therefore the 
             cbQosParentObjectsIndex of match ip http will be 1085.

             Assuming the router assigned a cbQosConfigIndex=1028 and 
             cbQosObjectsIndex=1088 to Policy cntlSNMP_Telnet. 
             Because it is attached to an interface, it has no parent 
             QoS object, and thus cbQosParentObjectsIndex=0. 
             In addition, because cntlSNMP_Telnet is also the service 
             policy of the interface, it has a unique cbQosPolicyIndex 
             assigned to it. In most cases, it would be the same as 
             the cbQosObjectsIndex, which is 1088 in this case.

             Assuming the router assigned a cbQosConfigIndex=1029 and
             cbQosObjectsIndex=1089 to ClassMap snmp, it is 
             directly being used by Policy cntlSNMP_Telnet, and 
             therefore the cbQosParentObjectsIndex of ClassMap snmp 
             will be 1088. 

             Assuming the router assigned a cbQosConfigIndex=1030 and
             cbQosObjectsIndex=1090 to match ip snmp, it is directly 
             used by ClassMap snmp, and therefore the 
             cbQosParentObjectsIndex of match ip snmp will be 1089.

             Assuming the router assigned a cbQosConfigIndex=1031 and
             cbQosObjectsIndex=1091 to shape average 8000 32 32, 
             it is directly used by ClassMap snmp, therefore the 
             cbQosParentObjectsIndex of match ip snmp will be 1089.

             Assuming the router assigned a cbQosConfigIndex=1032 and
             cbQosObjectsIndex=1092 to ClassMap Telnet, it is 
             directly being used by Policy cntlSNMP_Telnet, and 
             therefore the cbQosParentObjectsIndex of 
             ClassMap Telnet will be 1088. 

             Assuming the router assigned a cbQosConfigIndex=1033 and
             cbQosObjectsIndex=1093 to match ip telnet, it is 
             directly used by ClassMap Telnet, and therefore the 
             cbQosParentObjectsIndex of match ip telnet will be 1092.

             Assuming the router assigned a cbQosConfigIndex=1034 and
             cbQosObjectsIndex=1094 to shape 10000 32 32, it is 
             directly used by ClassMap telnet, therefore the 
             cbQosParentObjectsIndex of match ip telnet will be 1092.

             *** In Ethernet 0/2 ***
             Every objects will have a new and unique cbQosPolicyIndex 
             and cbQosObjectsIndex, but cbQosConfigIndex will be 
             shared across the same objects that are applied in 
             different places.

                **********************************
                         All Config Tables
                **********************************
           Accessing config related tables requires the same index 
           - cbQosConfigIndex.  (Per precedence based tables requires 
           a second index, which is IP precedence value) Users 
           should have already gone through the cbQosObjectsTable 
           at this point and understood each cbQosConfigIndex and the 
           corresponding QoS objects.  Users can uniquely identify 
           each QoS object defined on the router and query the 
           entries in each stats table on a per QoS object basis.  

                **********************************
                         All Stats Tables
                **********************************
           Accessing all stats related tables requires the same 
           2 indexes. They are cbQosPolicyIndex and cbQosObjectsIndex.
           (Per precedence based tables requires a third index, which 
           is IP precedence value) Users should have already gone 
           through the cbQosObjectsTable at this point and understood 
           the relationship of each cbQosPolicyIndex and 
           cbQosObjectsIndex pair and the corresponding QoS objects. 
           Users can uniquely identify each QoS object defined on the 
           router and query the entries in each stats table on a per 
           QoS object basis.
           "

        REVISION "200306090000Z"

        DESCRIPTION
                "Added controlPlane to the InterfaceType TC. 
                 Added cbQosEntityIndex to the cbQosServicePolicyTable."

        REVISION "200301210000Z"

        DESCRIPTION
                "Added compression(9) in QosObjectType TC for IPHC;
                 Added setMplsExpTopMost(11) in PoliceAction TC for 
                       POLICE;
                 Added mplsExpTopMost(8) in SetFeatureType TC for SET;
                 Added discardClass(13) in REDMechanism TC for WRED;
                 Added CbQosRateType TC for POLICE and SHAPE;
                 Added IPHCOption TC for IPHC;
                 Added cbQosPoliceCfgRateType, 
                       cbQosPoliceCfgPercentRateValue,
                       cbQosPoliceCfgPercentPirValue for POLICE;
                 Added cbQosTSCfgRateType,
                       cbQosTSCfgPercentRateValue for SHAPE;
                 Added cbQosSetCfgMplsExpTopMostValue for SET;
                 Added cbQosIPHCCfg and cbQosIPHCStats tables for IPHC."

        REVISION "200212030000Z"

        DESCRIPTION
                "Added new cbQosPoliceCfgRate64 to cbQosPoliceCfgEntry
                 table to support policing rates greater than fit in
                 the range defined for cbQosPoliceCfgRate"

        REVISION "200207240000Z"

        DESCRIPTION
                "Added support for ECN; Pir policing; multiple 
                 police actions; added MPLS-EXP/ATM-CLP/DR-DE/
                 L2Cos/DiscardClass marking in police action;
                 added MPLS-EXP and DiscardClass marking; 
                 modified ATM-CLP and FR-DE marking.
                 Added objects to handle queue depth unit type and 
                 queue depth pair related objects (e.g.,
                 cbQosQueueingCfgQLimitUnits and 
                 cbQosQueueingCfgAggregateQLimit pair) to support
                 queue depth in different units."
      
        REVISION "200103140000Z"

        DESCRIPTION
                "Added support for FR DE, ATM CLP and L2 marking.
                 Added Bandwidth remaining percent option"

        REVISION "200012080000Z"

        DESCRIPTION
                "Added support for Police Violate counters and
                 DSCP WRED counters"
        
        REVISION "200007130000Z"

        DESCRIPTION
                "Initial version of Class-based QoS configuration and 
                statistical parameters MIB"

        ::= { ciscoMgmt 166 }

--
--
-- Textual Conventions
--
--

QosObjectType ::= TEXTUAL-CONVENTION
        STATUS  current
        DESCRIPTION
        "Enums to indicate different QoS objects .
        policymap      - The object in query is a PolicyMap, being
                         attached on a logical interface.
        classmap       - The object in query is a ClassMap, being
                         used by it's parent PolicyMap.
        matchStatement - The object in query is a Match Statement,
                         being used by it's parent ClassMap.
        queueing       - The object in query is a queueing feature being
                         applied on the parent ClassMap.
        randomDetect   - The object in query is a Random Detect feature 
                         being applied on the parent ClassMap.
        trafficShaping - The object in query is a traffic-shaping 
                         feature being applied on the parent ClassMap.
        police         - The object in query is a Police feature being 
                         applied on the parent ClassMap.
        set            - The object in query is a Packet Marking 
                         feature being applied on the parent ClassMap.
        compression    - The object in query is a IP header compression
                         feature being applied on the parent ClassMap.
        "
        SYNTAX   INTEGER {
                          policymap(1),
                          classmap(2),
                          matchStatement(3),
                          queueing (4),
                          randomDetect (5),
                          trafficShaping (6),
                          police (7),
                          set (8),
                          compression (9)
                         }

TrafficDirection ::= TEXTUAL-CONVENTION
        STATUS  current
        DESCRIPTION
            "Enums to indicate whether the Policymap is for 
            Input or Output direction."

        SYNTAX   INTEGER {
                          input(1),
                          output(2)
                         }

QosClassInfo ::= TEXTUAL-CONVENTION
        STATUS  current
        DESCRIPTION
            "Enums to indicate whether the Classmap is for 
            Match All or Match Any."

        SYNTAX   INTEGER {
                          none(1),
                          matchAll(2),
                          matchAny(3)
                         }

QosMatchInfo ::= TEXTUAL-CONVENTION
        STATUS  current
        DESCRIPTION
            "Enums to indicate whether the MatchStatement is matching
            on negated criteria (Match Not)."

        SYNTAX   INTEGER {
                          none(1),
                          matchNot(2)
                         }

InterfaceType ::= TEXTUAL-CONVENTION
        STATUS  current
        DESCRIPTION
            "Enums to indicate the type of logical interface to which
             a particular service policy is attached.
        Main Interface   - Service policy is attached on the main 
                           interface.
        Sub Interface    - Service policy is attached on the sub 
                           interface.
        Frame Relay DLCI - Service policy is attached on the a 
                           Frame Relay DLCI.
        ATM VC           - Service policy is attached on the an ATM 
                           Virtual Circuit.
        Control Plane    - Service policy is attached to the control
                           plane of the device.
            "

        SYNTAX   INTEGER {
                          mainInterface(1),
                          subInterface(2),
                          frDLCI(3),
                          atmPVC(4),
                          controlPlane(5)
                         }

QueueingBandwidthUnits ::= TEXTUAL-CONVENTION
        STATUS  current
        DESCRIPTION
                "The units of the bandwidth, used to allocate
                bandwidth. Bandwidth can be either an absolute kbps 
                number, or be expressed as a percentage of the 
                available bandwidth.  

                kbps            Kilo bits Per Second
                percentage      %
                "

        SYNTAX  INTEGER { 
                          kbps(1), 
                          percentage(2),
                          percentageRemaining(3)  
                        }

TrafficShapingLimit ::= TEXTUAL-CONVENTION
        STATUS  current
        DESCRIPTION
                "The limit used by the traffic-shaping feature.
                This value may be 'average' or 'peak',
                which indicates whether it is shaping by average
                rate or peak rate."
 
        SYNTAX  INTEGER { 
                          average(1), 
                          peak(2) 
                        }

PoliceAction ::= TEXTUAL-CONVENTION
        STATUS  current
        DESCRIPTION
                "The available actions taken on packets upon 
                conforming, exceeding or violating the configured 
                police rate.

                Transmit - Transmit the packet if the packet conforms 
                           or exceeds the configured police rate.
                Set IP DSCP - Set the IP DSCP value if the packet
                              conforms or exceeds the configured police
                              rate.
                Set IP Precedence - Set the IP precedence value if
                                    the packet conforms or exceeds 
                                    the configured police rate.
                Set Qos Group - Set the QoS Group value if
                                the packet conforms or exceeds 
                                the configured police rate.
                Set MPLS Exp - Set the MPLS Experimental Imposition
                               vaule for the applicable action.
                Set ATM CLP  - Set the ATM CLP bit for the
                               applicable action.
                Set FR DE    - Set the FR DE bit for the
                               applicable action.
                Set L2 COS   - Set the 802.1p priority field in 802.1Q 
                               VLAN tag for the applicable action.
                Set Discard Class - Set the Discard Class value for the
                               applicable action.              
                Drop - Drop the packet if the packet conforms or 
                       exceeds the configured police rate.
                Set MPLS Exp TopMost - Set the MPLS Experimental 
                       TopMost vaule for the applicable action.
                "
 
        SYNTAX  INTEGER { 
                          transmit(1),
                          setIpDSCP(2),
                          setIpPrecedence(3),
                          setQosGroup(4),
                          drop(5),
                          setMplsExp(6),
                          setAtmClp(7),
                          setFrDe(8),
                          setL2Cos(9),
                          setDiscardClass(10),
                          setMplsExpTopMost(11)
                        }

SetFeatureType ::= TEXTUAL-CONVENTION
        STATUS  current
        DESCRIPTION
        "Bit-wise representation of packet marking feature available 
        today."

        SYNTAX  BITS {
                       ipDscp(0),
                       ipPrecedence(1),
                       qosGroupNumber(2),
                       frDeBit(3),
                       atmClpBit(4),
                       l2Cos(5),
                       mplsExp(6),
                       discardClass(7),
                       mplsExpTopMost(8)
                     }


REDMechanism ::= TEXTUAL-CONVENTION
        STATUS  current
        DESCRIPTION
                "This denotes whether Precedence-based or DSCP-based
                 mechanism is used with RED

                precedence      Based on IP precedence
                dscp            Based on DSCP values
                discardClass    Based on discard class
                "

        SYNTAX  INTEGER { 
                          precedence(1), 
                          dscp(2),
                          discardClass(3)
                        }

CbQosQueueUnitType ::= TEXTUAL-CONVENTION
        STATUS      current
        DESCRIPTION
                "A value that represents an unit type of queue 
                size.

                packets(1)   Represents the UNITS of 'packets' for
                             queue size.

                cells(2)     Represents the UNITS of 'cells' for 
                             queue size.

                bytes(3)     Represents the UNITS of 'bytes' for 
                             queue size.

                To support future extensions, the CbQosQueueUnitType 
                textual convention SHOULD NOT be sub-typed in object
                type definitions.

                It MAY be sub-typed in compliance statements in order to
                require only a subset of these queue size types for a 
                compliant implementation.

                Implementations must ensure that CbQosQueueUnitType 
                objects and any dependent object (e.g. CbQosQueueDepth) 
                are consistent. An inconsistentValue error must be 
                generated if an attempt to change an CbQosQueueUnitType 
                object would lead to an undefined CbQosQueueDepth value.
                In particular, CbQoSQueueUnitType/CbQosQueueDepth pairs 
                must be changed together if the CbQosQueueUnitType
                type changes (e.g. from packets(1) to cells(2))."
        SYNTAX  INTEGER {
                          packets(1),
                          cells(2),
                          bytes(3)
                         }

CbQosQueueDepth ::= TEXTUAL-CONVENTION
        STATUS      current
        DESCRIPTION
                "Denotes a generic Queue depth value.

                An CbQoSQueueDepth value is always interpreted within 
                the context of an CbQosQueueUnitType value. Every usage 
                of the CbQosQueueDepth textual convention is required to
                specify the CbQosQueueUnitType object which provides 
                the context. It is suggested that the 
                CbQoSQueueUnitType object is logically registered 
                before the object(s) which use the CbQosQueueDepth 
                textual convention if they appear in the same logical
                row. The value of an CbQosQueueDepth object must always
                be consistent with the value of the associated
                CbQosQueueUnitType object. Attempts to set an
                CbQosQueueDepth object to a value which is inconsistent 
                with the associated CbQosQueueUnitType must fail with 
                an inconsistentValue error."
       SYNTAX   Unsigned32

CbQosRateType ::= TEXTUAL-CONVENTION
        STATUS  current
        DESCRIPTION
                "The type of rate.  Rate type can be either an 
                absolute bps number, or be expressed as a percentage 
                of the available interface bandwidth.

                bps             Bits Per Second
                percentage      %
                "
        SYNTAX  INTEGER {
                          bps(1),
                          percentage(2)
                        }


IPHCOption ::= TEXTUAL-CONVENTION
        STATUS  current
        DESCRIPTION
                "Enums to indicate the type of IP header compression.
                rtp(1)         UDP/RTP compression.
                tcp(2)         TCP compression.
                bothRtpTcp(3)  Both UDP/RTP and TCP compression."

        SYNTAX  INTEGER {
                          rtp(1),
                          tcp(2),
                          bothRtpTcp(3)
                        }

--
-- Overview of MIB Objects:
--
-- Defines 2 groups of objects.
--

ciscoCBQosMIBObjects     OBJECT IDENTIFIER ::= { ciscoCBQosMIB 1 }
ciscocbQosMIBConformance OBJECT IDENTIFIER ::= { ciscoCBQosMIB 2 }

-- object groups

cbQosServicePolicy               OBJECT IDENTIFIER 
                                        ::= { ciscoCBQosMIBObjects 1 }
cbQosInterfacePolicy             OBJECT IDENTIFIER 
                                        ::= { ciscoCBQosMIBObjects 2 }
cbQosFrameRelayVCPolicy          OBJECT IDENTIFIER 
                                        ::= { ciscoCBQosMIBObjects 3 }
cbQosATMPVCPolicy                OBJECT IDENTIFIER 
                                        ::= { ciscoCBQosMIBObjects 4 }
cbQosObjects                     OBJECT IDENTIFIER 
                                        ::= { ciscoCBQosMIBObjects 5 }
cbQosPolicyMapCfg                OBJECT IDENTIFIER 
                                        ::= { ciscoCBQosMIBObjects 6 }
cbQosClassMapCfg                 OBJECT IDENTIFIER 
                                        ::= { ciscoCBQosMIBObjects 7 }
cbQosMatchStmtCfg                OBJECT IDENTIFIER 
                                        ::= { ciscoCBQosMIBObjects 8 }
cbQosQueueingCfg                 OBJECT IDENTIFIER 
                                        ::= { ciscoCBQosMIBObjects 9 }
cbQosREDCfg                      OBJECT IDENTIFIER 
                                        ::= { ciscoCBQosMIBObjects 10 }
cbQosREDClassCfg                 OBJECT IDENTIFIER 
                                        ::= { ciscoCBQosMIBObjects 11 }
cbQosPoliceCfg                   OBJECT IDENTIFIER 
                                        ::= { ciscoCBQosMIBObjects 12 }
cbQosTSCfg                       OBJECT IDENTIFIER 
                                        ::= { ciscoCBQosMIBObjects 13 }
cbQosSetCfg                      OBJECT IDENTIFIER 
                                        ::= { ciscoCBQosMIBObjects 14 }
cbQosClassMapStats               OBJECT IDENTIFIER 
                                        ::= { ciscoCBQosMIBObjects 15 }
cbQosMatchStmtStats              OBJECT IDENTIFIER 
                                        ::= { ciscoCBQosMIBObjects 16 }
cbQosPoliceStats                 OBJECT IDENTIFIER 
                                        ::= { ciscoCBQosMIBObjects 17 }
cbQosQueueingStats               OBJECT IDENTIFIER 
                                        ::= { ciscoCBQosMIBObjects 18 }
cbQosTSStats                     OBJECT IDENTIFIER 
                                        ::= { ciscoCBQosMIBObjects 19 }
cbQosREDClassStats               OBJECT IDENTIFIER 
                                        ::= { ciscoCBQosMIBObjects 20 }
cbQosPoliceActionCfg             OBJECT IDENTIFIER 
                                        ::= { ciscoCBQosMIBObjects 21 }
cbQosIPHCCfg                     OBJECT IDENTIFIER
                                        ::= { ciscoCBQosMIBObjects 22 }
cbQosIPHCStats                   OBJECT IDENTIFIER
                                        ::= { ciscoCBQosMIBObjects 23 }
--
-- The cbQosServicePolicy group
--

cbQosServicePolicyTable OBJECT-TYPE
        SYNTAX      SEQUENCE OF CbQosServicePolicyEntry
        MAX-ACCESS  not-accessible
        STATUS      current
        DESCRIPTION
           "This table describes the logical interfaces/media types
            and the policymap that are attached to it."
        ::= { cbQosServicePolicy 1 }

cbQosServicePolicyEntry OBJECT-TYPE
        SYNTAX      CbQosServicePolicyEntry
        MAX-ACCESS  not-accessible
        STATUS      current
        DESCRIPTION
           "Each entry in this table describes to which a logical 
           interface a given policymap is attached.  Depending on 
           the logical interface/media type, some fields may have
           meaningful values, and some may not.  Please see each
           individual descriptions.
            "

        INDEX { cbQosPolicyIndex }
        ::= { cbQosServicePolicyTable 1 }

CbQosServicePolicyEntry ::= SEQUENCE {
        cbQosPolicyIndex        Unsigned32,
        cbQosIfType             InterfaceType,
        cbQosPolicyDirection    TrafficDirection,
        cbQosIfIndex            InterfaceIndex,
        cbQosFrDLCI             DlciNumber,
        cbQosAtmVPI             Unsigned32,
        cbQosAtmVCI             Unsigned32,
        cbQosEntityIndex        EntPhysicalIndexOrZero
}

cbQosPolicyIndex OBJECT-TYPE
        SYNTAX      Unsigned32
        MAX-ACCESS  not-accessible
        STATUS      current
        DESCRIPTION
               "An arbitrary (system-assigned) index for all 
               service policies (PolicyMap that has been attached
               to a given logical interface)."
       ::= { cbQosServicePolicyEntry 1 }

cbQosIfType OBJECT-TYPE
        SYNTAX      InterfaceType
        MAX-ACCESS  read-only
        STATUS      current
        DESCRIPTION
                "This describes the logical interface/media type to
                 which this service policy is attached.
                 "
       ::= { cbQosServicePolicyEntry 2 }

cbQosPolicyDirection OBJECT-TYPE
        SYNTAX      TrafficDirection
        MAX-ACCESS  read-only
        STATUS      current
        DESCRIPTION
               "This indicates the direction of traffic for which 
               this service policy is applied.
               "
       ::= { cbQosServicePolicyEntry 3 }

cbQosIfIndex OBJECT-TYPE
        SYNTAX      InterfaceIndex
        MAX-ACCESS  read-only
        STATUS      current
        DESCRIPTION
                "ifIndex for the interface to which this service 
                is attached. This field makes sense only if the
                logical interface has a snmp ifIndex. For e.g. the
                value of this field is meaningless when the
                cbQosIfType is controlPlane.
                "
       ::= { cbQosServicePolicyEntry 4 }

cbQosFrDLCI  OBJECT-TYPE
        SYNTAX      DlciNumber
        MAX-ACCESS  read-only
        STATUS      current
        DESCRIPTION
                "DLCI for the FRVC to which this service is attached.
                This field only make sense if the service policy is
                attached to a Frame Relay DLCI.
                "
       ::= { cbQosServicePolicyEntry 5 }

cbQosAtmVPI  OBJECT-TYPE
        SYNTAX      Unsigned32 (0..4095)
        MAX-ACCESS  read-only
        STATUS      current
        DESCRIPTION
                "VPI for the ATMVC to which this service is attached.
                This field only make sense if the service policy is
                attached to a ATM VC.
                "
       ::= { cbQosServicePolicyEntry 6 }

cbQosAtmVCI  OBJECT-TYPE
        SYNTAX      Unsigned32 (0..65535)
        MAX-ACCESS  read-only
        STATUS      current
        DESCRIPTION 
                "VCI for the ATMVC to which this service is attached.
                This field only make sense if the service policy is
                attached to a ATM VC.
                "
       ::= { cbQosServicePolicyEntry 7 }

cbQosEntityIndex OBJECT-TYPE
        SYNTAX      EntPhysicalIndexOrZero
        MAX-ACCESS  read-only
        STATUS      current
        DESCRIPTION
                "In cases where the policy is attached to an entity
                 e.g. control-plane, this object represents the
                 entity physical index of the entity to which the
                 policy has been attached. A value zero may be 
                 returned if the policy is not attached to a physical
                 entity or the entPhysicalTable is not supported on 
                 the SNMP agent."
        ::= { cbQosServicePolicyEntry 8 }

--
-- End of the cbQosServicePolicy group
--


-- Beginning of cbQosInterfaceTable
--
cbQosInterfacePolicyTable OBJECT-TYPE
        SYNTAX      SEQUENCE OF CbQosInterfacePolicyEntry
        MAX-ACCESS  not-accessible
        STATUS      current
        DESCRIPTION
           "This table describes the service polices that are
           attached to main and sub interfaces.
           "
        ::= { cbQosInterfacePolicy 1 }

cbQosInterfacePolicyEntry OBJECT-TYPE
        SYNTAX      CbQosInterfacePolicyEntry
        MAX-ACCESS  not-accessible
        STATUS      current
        DESCRIPTION
           "Using ifIndex and Direction, each unique index pair
            translates to a service policy that is attached to a 
            main/sub interface, for particular traffic direction.
           "

        INDEX { ifIndex, cbQosPolicyDirection }
        ::= { cbQosInterfacePolicyTable 1 }

CbQosInterfacePolicyEntry ::= SEQUENCE {
        cbQosIFPolicyIndex      Unsigned32
}

cbQosIFPolicyIndex OBJECT-TYPE
        SYNTAX      Unsigned32
        MAX-ACCESS  read-only
        STATUS      current
        DESCRIPTION
               "An arbitrary (system-assigned) index for all 
                Service Policies. 

                This is identical to cbQosPolicyIndex.
                "
        ::= { cbQosInterfacePolicyEntry 1 }

-- End of cbQosInterfaceTable
--

-- Beginning of cbQosFrameRelayVCPolicy
--
cbQosFrameRelayPolicyTable OBJECT-TYPE
        SYNTAX      SEQUENCE OF CbQosFrameRelayPolicyEntry
        MAX-ACCESS  not-accessible
        STATUS      current
        DESCRIPTION
           "This table describes the service polices that are
            attached to Frame Relay DLCIs.
           "
        ::= { cbQosFrameRelayVCPolicy 1 }

cbQosFrameRelayPolicyEntry OBJECT-TYPE
        SYNTAX      CbQosFrameRelayPolicyEntry
        MAX-ACCESS  not-accessible
        STATUS      current
        DESCRIPTION
           "Using ifIndex, FR DLCI, and Direction, each unique 
           index combination translates to a service policy that 
           is attached to a FR DLCI, for particular traffic direction.
           "
        INDEX { ifIndex, cbQosFrDLCI, cbQosPolicyDirection }
        ::= { cbQosFrameRelayPolicyTable 1 }

CbQosFrameRelayPolicyEntry ::= SEQUENCE {
        cbQosFRPolicyIndex      Unsigned32
}

cbQosFRPolicyIndex OBJECT-TYPE
        SYNTAX      Unsigned32
        MAX-ACCESS  read-only
        STATUS      current
        DESCRIPTION
               "An arbitrary (system-assigned) index for all 
                Service Policies.
                
                This is identical to cbQosPolicyIndex.
                "
        ::= { cbQosFrameRelayPolicyEntry 1 }

-- End of cbQosFrameRelayTable
--


-- Beginning of cbQosATMPVCPolicy
--
cbQosATMPVCPolicyTable OBJECT-TYPE
        SYNTAX      SEQUENCE OF CbQosATMPVCPolicyEntry
        MAX-ACCESS  not-accessible
        STATUS      current
        DESCRIPTION
           "This table describes the policies that are attached to a
            ATM PVC."
        ::= { cbQosATMPVCPolicy 1 }

cbQosATMPVCPolicyEntry OBJECT-TYPE
        SYNTAX      CbQosATMPVCPolicyEntry
        MAX-ACCESS  not-accessible
        STATUS      current
        DESCRIPTION
           "Using ifIndex, VPI, VCI, and Direction, each unique 
           index combination translates to a service policy that 
           is attached to a ATM VC, for particular traffic direction.
           "
        INDEX { ifIndex, cbQosAtmVPI, 
                cbQosAtmVCI, cbQosPolicyDirection }
        ::= { cbQosATMPVCPolicyTable 1 }

CbQosATMPVCPolicyEntry ::= SEQUENCE {
        cbQosATMPolicyIndex     Unsigned32
}

cbQosATMPolicyIndex OBJECT-TYPE
        SYNTAX      Unsigned32
        MAX-ACCESS  read-only
        STATUS      current
        DESCRIPTION
               "An arbitrary (system-assigned) index for all 
                Service Policies.

                This is identical to cbQosPolicyIndex.
                "
        ::= { cbQosATMPVCPolicyEntry 1 }

-- End of cbQosATMPVCTable
--


-- The cbQosObjects group 
--
-- cbQosObjects Table

cbQosObjectsTable OBJECT-TYPE
        SYNTAX      SEQUENCE OF CbQosObjectsEntry
        MAX-ACCESS  not-accessible
        STATUS      current
        DESCRIPTION
            "This table specifies QoS objects (classmap, policymap, 
            match statements, and actions) hierarchy. This table also 
            provide relationship between each PolicyIndex/ObjectsIndex 
            pair and the ConfigIndex. ConfigIndex is essential for 
            querying any configuration tables.
            "
        ::= { cbQosObjects 1 }

cbQosObjectsEntry OBJECT-TYPE
        SYNTAX      CbQosObjectsEntry 
        MAX-ACCESS  not-accessible
        STATUS      current
        DESCRIPTION
           "A QoS object entry. Objects covered in this table are
            PolicyMap, ClassMap, Match Statements, and Actions.
            Each entry is indexed by system-generated cbQosPolicyIndex,
            and cbQosObjectsIndex, which represents a runtime instance 
            of a QoS object. In conjunction with the 
            cbQosParentObjectsIndex, a management station can 
            determine the hierarchical relationship of those QoS 
            objects. Given that classmaps and service policies can 
            be nested entites, each entry in this table represents a 
            unique instance of such object. Each runtime object 
            instance has a corresponding config object, which contains
            the configuration information of such QoS object. The
            config object is indexed by cbQosConfigIndex.
            "
        INDEX { cbQosPolicyIndex, cbQosObjectsIndex }
        ::= { cbQosObjectsTable 1 }

CbQosObjectsEntry ::= SEQUENCE {
        cbQosObjectsIndex        Unsigned32,
        cbQosConfigIndex         Unsigned32,
        cbQosObjectsType         QosObjectType,
        cbQosParentObjectsIndex  Unsigned32
}

cbQosObjectsIndex OBJECT-TYPE
        SYNTAX      Unsigned32
        MAX-ACCESS  not-accessible
        STATUS      current
        DESCRIPTION
               "An arbitrary (system-assigned) instance specific 
               index for cbQosObjectsEntry."

       ::= { cbQosObjectsEntry 1 }

cbQosConfigIndex OBJECT-TYPE
        SYNTAX      Unsigned32
        MAX-ACCESS  read-only
        STATUS      current
        DESCRIPTION
                "An arbitrary (system-assigned) config (instance 
                independent) index for each Object. Each objects having
                the same configuration share the same config index.
                "

       ::= { cbQosObjectsEntry 2 }

cbQosObjectsType OBJECT-TYPE
        SYNTAX          QosObjectType
        MAX-ACCESS      read-only
        STATUS          current
        DESCRIPTION
                "The type of the QoS object. 
                "
       ::= { cbQosObjectsEntry 3 }

cbQosParentObjectsIndex OBJECT-TYPE
        SYNTAX      Unsigned32
        MAX-ACCESS  read-only
        STATUS      current
        DESCRIPTION
               "The parent instance index of a QoS object.

                For a ClassMap, the parent index would be the index of 
                the attached PolicyMap.
 
                For a Match Statement, the parent index would be the 
                index of the ClassMap that uses this Match Statement.

                For an action, the parent index would be the 
                index of the ClassMap that applies such Action.

                For a non-hierarchical PolicyMap, the parent would be 
                the logical interface to which the policy is attached,
                thus the parent index would be 0.

                For a hierarchical PolicyMap, the parent index would 
                be the index of the ClassMap to which the nested 
                policy is attached."

       ::= { cbQosObjectsEntry 4 }
--
-- end of cbQosObjectsTable
--


--
-- Start of cbQosPolicyMapCfgTable
--
cbQosPolicyMapCfgTable OBJECT-TYPE
        SYNTAX      SEQUENCE OF CbQosPolicyMapCfgEntry
        MAX-ACCESS  not-accessible
        STATUS      current
        DESCRIPTION
            "This table specifies Policymap configuration information
            "
        ::= { cbQosPolicyMapCfg 1 }

cbQosPolicyMapCfgEntry OBJECT-TYPE
        SYNTAX      CbQosPolicyMapCfgEntry 
        MAX-ACCESS  not-accessible
        STATUS      current
        DESCRIPTION
           "Each entry in this table describes configuration information
           about a policymap. The information includes: Name, and it's
           description. This table contains configuration information 
           only, no statistics associated with it. Therefore, it is 
           indexed by the cbQosConfigIndex of each PolicyMap.
           "
        INDEX { cbQosConfigIndex }
        ::= { cbQosPolicyMapCfgTable 1 }

CbQosPolicyMapCfgEntry ::= SEQUENCE {
        cbQosPolicyMapName       DisplayString,
        cbQosPolicyMapDesc       DisplayString
}

cbQosPolicyMapName OBJECT-TYPE
        SYNTAX      DisplayString (SIZE (0..255))
        MAX-ACCESS  read-only
        STATUS      current
        DESCRIPTION
               "Name of the Policymap."

       ::= { cbQosPolicyMapCfgEntry 1 }

cbQosPolicyMapDesc OBJECT-TYPE
        SYNTAX      DisplayString (SIZE (0..255))
        MAX-ACCESS  read-only
        STATUS      current
        DESCRIPTION
               "Description of the PolicyMap."

       ::= { cbQosPolicyMapCfgEntry 2 }
--
-- Start of cbQosPolicyMapCfgTable
--


--
-- Start of cbQosCMCfg Group
--
cbQosCMCfgTable OBJECT-TYPE
        SYNTAX      SEQUENCE OF CbQosCMCfgEntry
        MAX-ACCESS  not-accessible
        STATUS      current
        DESCRIPTION
            "This table specifies ClassMap configuration information
            "
        ::= { cbQosClassMapCfg 1 }

cbQosCMCfgEntry OBJECT-TYPE
        SYNTAX      CbQosCMCfgEntry 
        MAX-ACCESS  not-accessible
        STATUS      current
        DESCRIPTION
           "Each entry in this table describes configuration information
           about a classmap. The information includes: Name, and it's
           description and whether it is a Match-All or Match-Any
           class. This table contains configuration information only,
           no statistics associated with it. Therefore, it is indexed
           by the cbQosConfigIndex of each ClassMap.
           "
        INDEX { cbQosConfigIndex }
        ::= { cbQosCMCfgTable 1 }

CbQosCMCfgEntry ::= SEQUENCE {
        cbQosCMName DisplayString,
        cbQosCMDesc DisplayString,
        cbQosCMInfo QosClassInfo
}

cbQosCMName OBJECT-TYPE
        SYNTAX      DisplayString (SIZE (0..255))
        MAX-ACCESS  read-only
        STATUS      current
        DESCRIPTION
               "Name of the Classmap."

       ::= { cbQosCMCfgEntry 1 }

cbQosCMDesc OBJECT-TYPE
        SYNTAX      DisplayString (SIZE (0..255))
        MAX-ACCESS  read-only
        STATUS      current
        DESCRIPTION
               "Description of the Classmap."

       ::= { cbQosCMCfgEntry 2 }

cbQosCMInfo OBJECT-TYPE
        SYNTAX      QosClassInfo
        MAX-ACCESS  read-only
        STATUS      current
        DESCRIPTION
               "Match all vs Match any in a given class."

       ::= { cbQosCMCfgEntry 3 }
--
-- End of cbQosCMCfg Group
--


--
-- Start of cbQosMatchStmtCfgTable
--
cbQosMatchStmtCfgTable OBJECT-TYPE
        SYNTAX      SEQUENCE OF CbQosMatchStmtCfgEntry
        MAX-ACCESS  not-accessible
        STATUS      current
        DESCRIPTION
            "This table specifies ClassMap configuration information
            "
        ::= { cbQosMatchStmtCfg 1 }

cbQosMatchStmtCfgEntry OBJECT-TYPE
        SYNTAX      CbQosMatchStmtCfgEntry 
        MAX-ACCESS  not-accessible
        STATUS      current
        DESCRIPTION
           "Each entry in this table describes configuration information
           about a MatchStatement. The information includes: Name, 
           and whether it is a Match or Match-Not
           statement. This table contains configuration information 
           only, no statistics associated with it. Therefore, it is 
           indexed by the cbQosConfigIndex of each MatchStatement.
           "
        INDEX { cbQosConfigIndex }
        ::= { cbQosMatchStmtCfgTable 1 }

CbQosMatchStmtCfgEntry ::= SEQUENCE {
        cbQosMatchStmtName DisplayString,
        cbQosMatchStmtInfo QosMatchInfo
}

cbQosMatchStmtName OBJECT-TYPE
        SYNTAX      DisplayString (SIZE (0..255))
        MAX-ACCESS  read-only
        STATUS      current
        DESCRIPTION
               "Name of the Match Statement."

       ::= { cbQosMatchStmtCfgEntry 1 }

cbQosMatchStmtInfo OBJECT-TYPE
        SYNTAX      QosMatchInfo
        MAX-ACCESS  read-only
        STATUS      current
        DESCRIPTION
               "Match vs Match Not in a given class."

       ::= { cbQosMatchStmtCfgEntry 2 }
--
-- End of cbQosMatchStmtCfgTable
--


--
-- Start of cbQosQueueingCfgTable
--
cbQosQueueingCfgTable OBJECT-TYPE
        SYNTAX      SEQUENCE OF CbQosQueueingCfgEntry
        MAX-ACCESS  not-accessible
        STATUS      current
        DESCRIPTION
            "This table specifies Queueing Action configuration 
            information
            "
            ::= { cbQosQueueingCfg 1 }

cbQosQueueingCfgEntry OBJECT-TYPE
        SYNTAX      CbQosQueueingCfgEntry 
        MAX-ACCESS  not-accessible
        STATUS      current
        DESCRIPTION
           "Each entry in this table describes configuration 
           information about a queueing action. The information 
           includes: Bandwidth, Units, Flow Enabled, Priority Enabled, 
           and Q size.

           This table contains configuration information only,
           no statistics associated with it. Therefore, it is indexed
           by the cbQosConfigIndex of each Queueing Action.
           "

        INDEX { cbQosConfigIndex }
        ::= { cbQosQueueingCfgTable 1 }

CbQosQueueingCfgEntry ::= SEQUENCE {
        cbQosQueueingCfgBandwidth        Integer32,
        cbQosQueueingCfgBandwidthUnits   QueueingBandwidthUnits,
        cbQosQueueingCfgFlowEnabled      TruthValue,
        cbQosQueueingCfgPriorityEnabled  TruthValue,
        cbQosQueueingCfgAggregateQSize   Integer32,
        cbQosQueueingCfgIndividualQSize  Integer32,
        cbQosQueueingCfgDynamicQNumber   Integer32,
        cbQosQueueingCfgPrioBurstSize    Unsigned32,
        cbQosQueueingCfgQLimitUnits      CbQosQueueUnitType,
        cbQosQueueingCfgAggregateQLimit  CbQosQueueDepth
}

cbQosQueueingCfgBandwidth OBJECT-TYPE
        SYNTAX  Integer32 (0..2000000)
        MAX-ACCESS  read-only
        STATUS  current
        DESCRIPTION
                "The configured bandwidth allocated to this traffic 
                class.  In the case of a bandwidth policy, this value 
                represents a minimum b/w guarantee for the traffic 
                class.  In the case of a priority policy, this value 
                represents the maximum rate at which priority service 
                is guaranteed."
 
        ::= { cbQosQueueingCfgEntry 1 }
 
cbQosQueueingCfgBandwidthUnits OBJECT-TYPE
        SYNTAX  QueueingBandwidthUnits
        MAX-ACCESS  read-only
        STATUS  current
        DESCRIPTION
                "Units of the accompanying cbQosQueueingCfgbandwidth
                 parameter.
                 "
 
        ::= { cbQosQueueingCfgEntry 2 }
 
cbQosQueueingCfgFlowEnabled OBJECT-TYPE
        SYNTAX  TruthValue
        MAX-ACCESS  read-only
        STATUS  current
        DESCRIPTION
                "Boolean to indicate if flow-based fair-queue is 
                 enabled for this class."
 
        ::= { cbQosQueueingCfgEntry 3 }
 
cbQosQueueingCfgPriorityEnabled OBJECT-TYPE
        SYNTAX  TruthValue
        MAX-ACCESS  read-only
        STATUS  current
        DESCRIPTION
                "Boolean to indicate if low latency queueing
                 (priority) is enabled for this class."
 
        ::= { cbQosQueueingCfgEntry 4 }
 
cbQosQueueingCfgAggregateQSize OBJECT-TYPE
        SYNTAX  Integer32 (0..65535)
        UNITS   "Packets"
        MAX-ACCESS  read-only
        STATUS  deprecated
        DESCRIPTION
                "Maximum number of packets that can be held in all the
                 individual queues associated with this class
                 before packets are dropped. This object is deprecated
                 by cbQosQueueingCfgAggregateQLimit."
 
        ::= { cbQosQueueingCfgEntry 5 }
 
cbQosQueueingCfgIndividualQSize OBJECT-TYPE
        SYNTAX  Integer32 (1..32768)
        UNITS   "Packets"
        MAX-ACCESS  read-only
        STATUS  current
        DESCRIPTION
                "Maximum number of packets that can be held in an
                 individual Flow-based fair-queue associated with this 
                 class before it drops packets (once the AggregateQSize
                 has been reached).

                 This field only makes sense in the context of 
                 Flow-based fair-queueing.
                "
 
        ::= { cbQosQueueingCfgEntry 6 }

cbQosQueueingCfgDynamicQNumber OBJECT-TYPE
        SYNTAX  Integer32 (1..32768)
        MAX-ACCESS  read-only
        STATUS  current
        DESCRIPTION
                "Number of dynamic queues supported when
                 flow-based fair-queue is in use."
 
        ::= { cbQosQueueingCfgEntry 7 }

cbQosQueueingCfgPrioBurstSize OBJECT-TYPE
        SYNTAX  Unsigned32 (32..64000000)
        UNITS   "Bytes"
        MAX-ACCESS  read-only
        STATUS  current
        DESCRIPTION
                "In the priority queue, this is the number of bytes 
                 allowed in a single burst. 
                 This parameter only makes sense if Priority is enabled
                "
 
        ::= { cbQosQueueingCfgEntry 8 }

cbQosQueueingCfgQLimitUnits OBJECT-TYPE
        SYNTAX  CbQosQueueUnitType
        MAX-ACCESS  read-only
        STATUS  current
        DESCRIPTION
                "Represents the unit type of
                 cbQosQueueingCfgAggregateQLimit object."

        ::= { cbQosQueueingCfgEntry 9 }

cbQosQueueingCfgAggregateQLimit OBJECT-TYPE
        SYNTAX  CbQosQueueDepth
        MAX-ACCESS  read-only
        STATUS  current
        DESCRIPTION
                "Maximum allowed queue size for all the individual 
                queues associated with this class. When the queue size
                exceed this value, the packets will be dropped."

        ::= { cbQosQueueingCfgEntry 10 }

--
-- End of cbQosQueueingCfg Group
--


-- The cbQosREDCfg group
--
-- cbQosREDTable
 
cbQosREDCfgTable OBJECT-TYPE
        SYNTAX      SEQUENCE OF CbQosREDCfgEntry
        MAX-ACCESS  not-accessible
        STATUS      current
        DESCRIPTION
            "This table specifies WRED Action configuration 
            information
            "
        ::= { cbQosREDCfg 1 }
 
cbQosREDCfgEntry OBJECT-TYPE
        SYNTAX      CbQosREDCfgEntry
        MAX-ACCESS  not-accessible
        STATUS      current
        DESCRIPTION
           "Each entry in this table describes configuration 
           information about a WRED Action.  The table holds global 
           (per traffic class) configuration like: Expon Weight
           and Mean Q size.

           This table contains configuration information only,
           no statistics associated with it. Therefore, it is indexed
           by the cbQosConfigIndex of each WRED Action.
           "
        INDEX { cbQosConfigIndex }
        ::= { cbQosREDCfgTable 1 }
 
CbQosREDCfgEntry ::= SEQUENCE {
        cbQosREDCfgExponWeight    Integer32,
        cbQosREDCfgMeanQsize      Integer32,
        cbQosREDCfgDscpPrec       REDMechanism,
        cbQosREDCfgECNEnabled     TruthValue
}
 
 
cbQosREDCfgExponWeight OBJECT-TYPE
        SYNTAX  Integer32 (1..16)
        MAX-ACCESS  read-only
        STATUS  current
        DESCRIPTION
               "The decay factor for the queue average calculation.
                The decay factor is equal to raising 2 to the power 
                of N, where N could be up to 16. 
                The smaller the number, the faster it decays."
 
        ::= { cbQosREDCfgEntry 1 }
 
 
cbQosREDCfgMeanQsize OBJECT-TYPE
        SYNTAX  Integer32 (0..65535)
        UNITS   "Packets"
        MAX-ACCESS  read-only
        STATUS  deprecated
        DESCRIPTION
                "The average queue size, computed and used by the WRED
                algorithm. This is deprecated by cbQosREDMeanQsize."
 
        ::= { cbQosREDCfgEntry 2 }

cbQosREDCfgDscpPrec OBJECT-TYPE
        SYNTAX  REDMechanism
        MAX-ACCESS  read-only
        STATUS  current
        DESCRIPTION
                "The Classification mechanism used by RED - precedence,
                 dscp, or discardClass based."
 
        ::= { cbQosREDCfgEntry 3 }

cbQosREDCfgECNEnabled OBJECT-TYPE
        SYNTAX  TruthValue
        MAX-ACCESS  read-only
        STATUS  current
        DESCRIPTION
                "Boolean to indicate if explicit congestion notification
                enabled for this class."

        ::= { cbQosREDCfgEntry 4 }

--
-- end of cbQosREDCfgTable
--


--
-- cbQosREDClassCfg Group
 
cbQosREDClassCfgTable OBJECT-TYPE
        SYNTAX      SEQUENCE OF CbQosREDClassCfgEntry
        MAX-ACCESS  not-accessible
        STATUS      current
        DESCRIPTION
            "This table specifies WRED Action configuration 
            information on a per IP precedence basis.
            "
        ::= { cbQosREDClassCfg 1 }
 
cbQosREDClassCfgEntry OBJECT-TYPE
        SYNTAX      CbQosREDClassCfgEntry
        MAX-ACCESS  not-accessible
        STATUS      current
        DESCRIPTION
           "Each entry in this table describes configuration information
           about a WRED Action.  The table holds the per IP precedence
           based WRED configuration parameters. 

           This table contains configuration information only,
           no statistics associated with it. Therefore, it is indexed
           by the cbQosConfigIndex and cbQosREDValue 
           of each WRED Action.
           "

        INDEX { cbQosConfigIndex, cbQosREDValue}
        ::= { cbQosREDClassCfgTable 1 }
 
CbQosREDClassCfgEntry ::= SEQUENCE {
        cbQosREDValue                  Integer32,
        cbQosREDCfgMinThreshold        Integer32,
        cbQosREDCfgMaxThreshold        Integer32,
        cbQosREDCfgPktDropProb         Integer32,
        cbQosREDClassCfgThresholdUnit  CbQosQueueUnitType,
        cbQosREDClassCfgMinThreshold   CbQosQueueDepth,
        cbQosREDClassCfgMaxThreshold   CbQosQueueDepth
}
 
cbQosREDValue OBJECT-TYPE
        SYNTAX  Integer32 (0..63)
        MAX-ACCESS  not-accessible
        STATUS  current
        DESCRIPTION
                "The IP precedence or IP DSCP of this entry."
 
        ::= { cbQosREDClassCfgEntry 1 }
 
cbQosREDCfgMinThreshold OBJECT-TYPE
        SYNTAX  Integer32 (1..32768)
        UNITS   "Packets"
        MAX-ACCESS  read-only
        STATUS  deprecated
        DESCRIPTION
                "Minimum threshold in number of packets. When the 
                average queue length reaches this number, WRED begins 
                to drop packets with the specified IP precedence.
                This is deprecated by cbQosREDClassCfgMinThreshold."
 
        ::= { cbQosREDClassCfgEntry 2 }
 
cbQosREDCfgMaxThreshold OBJECT-TYPE
        SYNTAX  Integer32 (1..32768)
        UNITS   "Packets"
        MAX-ACCESS  read-only
        STATUS  deprecated
        DESCRIPTION
                "Maximum threshold in number of packets. When the 
                average queue length exceeds this number, WRED drops 
                all packets with the specified IP precedence.
                This is deprecated by cbQosREDClassCfgMaxThreshold."
 
        ::= { cbQosREDClassCfgEntry 3 }
 
cbQosREDCfgPktDropProb OBJECT-TYPE
        SYNTAX  Integer32 (1..65536)
        UNITS   ""
        MAX-ACCESS  read-only
        STATUS  current
        DESCRIPTION
                 "Denominator for the fraction of packets dropped when 
                  the average queue depth is MaxDepthThreshold. For 
                  example, if the denominator is 10, one out of every 10
                  packets is dropped when the average queue is at the 
                  MaxDepthThreshold."  
 
        ::= { cbQosREDClassCfgEntry 4 }

cbQosREDClassCfgThresholdUnit OBJECT-TYPE
        SYNTAX  CbQosQueueUnitType
        MAX-ACCESS  read-only
        STATUS  current
        DESCRIPTION
                "Represents the unit type to measure the RED thresholds.
                 The objects covered are cbQosREDClassCfgMinThreshold
                 and cbQosREDClassCfgMaxThreshold."

        ::= { cbQosREDClassCfgEntry 5 }

cbQosREDClassCfgMinThreshold OBJECT-TYPE
        SYNTAX  CbQosQueueDepth
        MAX-ACCESS  read-only
        STATUS  current
        DESCRIPTION
                "The minimum WRED threshold value. When the average
                queue length reaches this number, WRED begins to 
                drop packets according to REDMechanism specificed
                in cbQosREDCfgDscpPrec."

        ::= { cbQosREDClassCfgEntry 6 }
 

cbQosREDClassCfgMaxThreshold OBJECT-TYPE
        SYNTAX  CbQosQueueDepth
        MAX-ACCESS  read-only
        STATUS  current
        DESCRIPTION
                "The maximum WRED threshold value. When the average
                queue length exceeds this number, WRED drops all 
                packets according to REDMechanism specificed
                in cbQosREDCfgDscpPrec."

        ::= { cbQosREDClassCfgEntry 7 }
 
-- end of cbQosREDClassCfg Group


--
-- Start of cbQosPoliceCfg Group
--

cbQosPoliceCfgTable OBJECT-TYPE
        SYNTAX      SEQUENCE OF CbQosPoliceCfgEntry
        MAX-ACCESS  not-accessible
        STATUS      current
        DESCRIPTION
            "This table specifies Police Action configuration 
            information.
            "
        ::= { cbQosPoliceCfg 1 }

cbQosPoliceCfgEntry OBJECT-TYPE
        SYNTAX      CbQosPoliceCfgEntry
        MAX-ACCESS  not-accessible
        STATUS      current
        DESCRIPTION
           "Each entry in this table describes configuration information
           about a Police Action.  The table holds Policy 
           configuration parameters, such as rate, burst size, and 
           actions based on traffic rates.

           This table contains configuration information only,
           no statistics associated with it. Therefore, it is indexed
           by the cbQosConfigIndex.
           "
        INDEX { cbQosConfigIndex }
        ::= { cbQosPoliceCfgTable 1 }

CbQosPoliceCfgEntry ::= SEQUENCE {
        cbQosPoliceCfgRate               Unsigned32,
        cbQosPoliceCfgBurstSize          Unsigned32,
        cbQosPoliceCfgExtBurstSize       Unsigned32,
        cbQosPoliceCfgConformAction      PoliceAction,
        cbQosPoliceCfgConformSetValue    Unsigned32,
        cbQosPoliceCfgExceedAction       PoliceAction,
        cbQosPoliceCfgExceedSetValue     Unsigned32,
        cbQosPoliceCfgViolateAction      PoliceAction,
        cbQosPoliceCfgViolateSetValue    Unsigned32,
        cbQosPoliceCfgPir                Unsigned32,
        cbQosPoliceCfgRate64             Unsigned64,
        cbQosPoliceCfgRateType           CbQosRateType,
        cbQosPoliceCfgPercentRateValue   Unsigned32,
        cbQosPoliceCfgPercentPirValue    Unsigned32
}

cbQosPoliceCfgRate OBJECT-TYPE
        SYNTAX  Unsigned32 (8000..2000000000)
        UNITS   "bits/second"
        MAX-ACCESS  read-only
        STATUS  current
        DESCRIPTION
                "The committed policing rate. This is the sustained
                rate permitted by policing.

                If a committed policing rate greater than 2000000000
                is configurable on the system, then the configured
                rate is available in cbQosPoliceCfgRate64."

        ::= { cbQosPoliceCfgEntry 1 }

cbQosPoliceCfgBurstSize OBJECT-TYPE
        SYNTAX  Unsigned32 (1000..512000000)
        UNITS   "Octets"
        MAX-ACCESS  read-only
        STATUS  current
        DESCRIPTION
                "The amount of traffic, in bytes, in excess of the 
                committed policing rate that will be permitted by 
                the policing feature."

        ::= { cbQosPoliceCfgEntry 2 }

cbQosPoliceCfgExtBurstSize OBJECT-TYPE
        SYNTAX  Unsigned32 (1000..512000000)
        UNITS   "Octets"
        MAX-ACCESS  read-only
        STATUS  current
        DESCRIPTION
                "The amount of traffic, in bytes, in excess of the 
                burst limit, which may be conditionally permitted 
                by the policing feature. The probability that the 
                traffic is not permitted increases as the received 
                burst size increases."

        ::= { cbQosPoliceCfgEntry 3 }

cbQosPoliceCfgConformAction OBJECT-TYPE
        SYNTAX      PoliceAction
        MAX-ACCESS  read-only
        STATUS  deprecated
        DESCRIPTION
                "Action to be taken when the traffic is within the
                configured rate, that is, the traffic rate is 
                conforming.
                This object is deprecated and defined in 
                cqQosPoliceActionCfgTable.
                "
        ::= { cbQosPoliceCfgEntry 4 }

cbQosPoliceCfgConformSetValue OBJECT-TYPE
        SYNTAX      Unsigned32 (1..99)
        MAX-ACCESS  read-only
        STATUS  deprecated
        DESCRIPTION
                "New packet attribute values for each packets that 
                conforms to the configured Police rate.
                This object is deprecated and defined in 
                cqQosPoliceActionCfgTable.
                "
        ::= { cbQosPoliceCfgEntry 5 }

cbQosPoliceCfgExceedAction OBJECT-TYPE
        SYNTAX      PoliceAction
        MAX-ACCESS  read-only
        STATUS  deprecated
        DESCRIPTION
                "Action to be taken when the traffic exceeds the 
                configured rate, that is, the traffic is 
                non-conforming.
                This object is deprecated and defined in 
                cqQosPoliceActionCfgTable.
                "
        ::= { cbQosPoliceCfgEntry 6 }

cbQosPoliceCfgExceedSetValue OBJECT-TYPE
        SYNTAX      Unsigned32 (1..99)
        MAX-ACCESS  read-only
        STATUS  deprecated
        DESCRIPTION
                "New packet attribute values for each packets that 
                conforms to the configured Police rate.
                This object is deprecated and defined in 
                cqQosPoliceActionCfgTable.
                "
        ::= { cbQosPoliceCfgEntry 7 }

cbQosPoliceCfgViolateAction OBJECT-TYPE
        SYNTAX      PoliceAction
        MAX-ACCESS  read-only
        STATUS  deprecated
        DESCRIPTION
                "Action to be taken when the traffic exceeds the
                conform and exceed token buckets.
                This object is deprecated and defined in 
                cqQosPoliceActionCfgTable.
                "
        ::= { cbQosPoliceCfgEntry 8 }

cbQosPoliceCfgViolateSetValue OBJECT-TYPE
        SYNTAX      Unsigned32 (1..99)
        MAX-ACCESS  read-only
        STATUS  deprecated
        DESCRIPTION
                "New packet attribute values for each packets that
                 conforms to the Police violate action. The packet
                 attibute values depend on the action that is taken
                 for the particular packet. For example, if the 
                 action was to set the dscp value, this entry describes
                 the value it is set to. 
                 This object is deprecated and defined in 
                 cqQosPoliceActionCfgTable.
                "
        ::= { cbQosPoliceCfgEntry 9 }

cbQosPoliceCfgPir OBJECT-TYPE
        SYNTAX  Unsigned32 (8000..2000000000)
        UNITS   "bits/second"
        MAX-ACCESS  read-only
        STATUS  current
        DESCRIPTION
                "The committed policing rate. This is the peak
                rate permitted by two rate policing."

        ::= { cbQosPoliceCfgEntry 10 }

cbQosPoliceCfgRate64 OBJECT-TYPE
        SYNTAX  Unsigned64
        UNITS   "bits/second"
        MAX-ACCESS  read-only
        STATUS  current
        DESCRIPTION
                "The committed policing rate. This is the sustained
                rate permitted by policing."

        ::= { cbQosPoliceCfgEntry 11 }

cbQosPoliceCfgRateType OBJECT-TYPE
        SYNTAX  CbQosRateType 
        MAX-ACCESS  read-only
        STATUS  current
        DESCRIPTION
                "The rate type that configured for CIR & PIR.
                1 means rates are configured in bps.
                2 means rates are configured in percentage."

        ::= { cbQosPoliceCfgEntry 12 }

cbQosPoliceCfgPercentRateValue OBJECT-TYPE
        SYNTAX  Unsigned32 (0..100)
        UNITS   "% of Interface Bandwidth"
        MAX-ACCESS  read-only
        STATUS  current
        DESCRIPTION
                "The committed policing rate in percentage.  Its value
                is valid only when cbQosPoliceCfgRateType equals to 2."

        ::= { cbQosPoliceCfgEntry 13 }

cbQosPoliceCfgPercentPirValue OBJECT-TYPE
        SYNTAX  Unsigned32 (0..100)
        UNITS   "% of Interface Bandwidth"
        MAX-ACCESS  read-only
        STATUS  current
        DESCRIPTION
                "The peak policing rate in percentage. Its value is
                valid only when cbQosPoliceCfgRateType equals to 2."

        ::= { cbQosPoliceCfgEntry 14 }
--
-- end of cbQosPoliceCfg Group
--

--
-- Start of cbQosPoliceActionCfg Group
--

cbQosPoliceActionCfgTable OBJECT-TYPE
        SYNTAX      SEQUENCE OF CbQosPoliceActionCfgEntry
        MAX-ACCESS  not-accessible
        STATUS      current
        DESCRIPTION
            "This table specifies Police Action configuration 
            information.
            "
        ::= { cbQosPoliceActionCfg 1 }

cbQosPoliceActionCfgEntry OBJECT-TYPE
        SYNTAX      CbQosPoliceActionCfgEntry
        MAX-ACCESS  not-accessible
        STATUS      current
        DESCRIPTION
           "Each entry in this table describes configuration information
           about Actions for one Police.  The table holds Police 
           action specific configuration parameters.
           This table is a sub-table for cbQosPoliceCfgTable. There is
           a 1-to-1 association between one entry here and one entry in 
           cbQosPoliceCfgTable. 
           This table contains configuration information only,
           no statistics associated with it. 
           This table has two indices. The first is cbQosConfigIndex 
           which is drived directly from cbQosPoliceCfgTable to keep the
           1-to-1 mapping nature between two tables. 
           The second is cbQosPoliceActionCfgIndex used to reference 
           the actual actions configured. The maximum number of actions
           supported is determined by the system, which is 5 currently.
           "
        INDEX { cbQosConfigIndex, cbQosPoliceActionCfgIndex }
        ::= { cbQosPoliceActionCfgTable 1 }

CbQosPoliceActionCfgEntry ::= SEQUENCE {
        cbQosPoliceActionCfgIndex           Unsigned32,
        cbQosPoliceActionCfgConform         PoliceAction,
        cbQosPoliceActionCfgConformSetValue Unsigned32,
        cbQosPoliceActionCfgExceed          PoliceAction,
        cbQosPoliceActionCfgExceedSetValue  Unsigned32,
        cbQosPoliceActionCfgViolate         PoliceAction,
        cbQosPoliceActionCfgViolateSetValue Unsigned32
}

cbQosPoliceActionCfgIndex OBJECT-TYPE
        SYNTAX      Unsigned32
        MAX-ACCESS  not-accessible
        STATUS      current
        DESCRIPTION
                "An arbitrary (system-assigned) index for police 
                actions that are defined by a police configuration.
                "
       ::= { cbQosPoliceActionCfgEntry 1 }

cbQosPoliceActionCfgConform OBJECT-TYPE
        SYNTAX      PoliceAction
        MAX-ACCESS  read-only
        STATUS      current
        DESCRIPTION
                "Action to be taken when the traffic exceeds the
                conform and exceed token buckets.
                "
        ::= { cbQosPoliceActionCfgEntry 2 }

cbQosPoliceActionCfgConformSetValue OBJECT-TYPE
        SYNTAX      Unsigned32 (0..99)
        MAX-ACCESS  read-only
        STATUS      current
        DESCRIPTION
                "New packet attribute values for each packet set by 
                police action defined in cbQosPoliceActionCfgConform.
                This object will be set to zero if the corresponding
                police action does not require a set value, such as 
                no action, drop action or transmit action.
                "
        ::= { cbQosPoliceActionCfgEntry 3 }

cbQosPoliceActionCfgExceed OBJECT-TYPE
        SYNTAX      PoliceAction
        MAX-ACCESS  read-only
        STATUS      current
        DESCRIPTION
                "Action to be taken when the traffic exceeds the
                conform and exceed token buckets.
                "
        ::= { cbQosPoliceActionCfgEntry 4 }

cbQosPoliceActionCfgExceedSetValue OBJECT-TYPE
        SYNTAX      Unsigned32 (0..99)
        MAX-ACCESS  read-only
        STATUS      current
        DESCRIPTION
                "New packet attribute values for each packet set by 
                police action defined in cbQosPoliceActionCfgExceed.
                This object will be set to zero if the corresponding
                police action does not require a set value, such as 
                no action, drop action or transmit action.
                "
        ::= { cbQosPoliceActionCfgEntry 5 }

cbQosPoliceActionCfgViolate OBJECT-TYPE
        SYNTAX      PoliceAction
        MAX-ACCESS  read-only
        STATUS      current
        DESCRIPTION
                "Action to be taken when the traffic exceeds the
                conform and exceed token buckets.
                "
        ::= { cbQosPoliceActionCfgEntry 6 }

cbQosPoliceActionCfgViolateSetValue OBJECT-TYPE
        SYNTAX      Unsigned32 (0..99)
        MAX-ACCESS  read-only
        STATUS      current
        DESCRIPTION
                "New packet attribute values for each packet set by 
                police action defined in cbQosPoliceActionCfgViolate.
                This object will be set to zero if the corresponding
                police action does not require a set value, such as 
                no action, drop action or transmit action.
                "
        ::= { cbQosPoliceActionCfgEntry 7 }

--
-- end of cbQosPoliceActionCfg Group
--

--
-- The cbQosTSCfg group
--
-- cbQosTSCfgTable
 
cbQosTSCfgTable OBJECT-TYPE
        SYNTAX      SEQUENCE OF CbQosTSCfgEntry
        MAX-ACCESS  not-accessible
        STATUS      current
        DESCRIPTION
            "This table specifies traffic-shaping Action configuration 
            information.
            "
        ::= { cbQosTSCfg 1 }
 
cbQosTSCfgEntry OBJECT-TYPE
        SYNTAX      CbQosTSCfgEntry
        MAX-ACCESS  not-accessible
        STATUS      current
        DESCRIPTION
           "Each entry in this table describes configuration information
           about a traffic-shaping Action.  The table holds Traffic
           Shaping configuration parameters, such as rate, burst size, 
           and Shaping types.

           This table contains configuration information only,
           no statistics associated with it. Therefore, it is indexed
           by the cbQosConfigIndex.
           "
        INDEX { cbQosConfigIndex }
        ::= { cbQosTSCfgTable 1 }
 
CbQosTSCfgEntry ::= SEQUENCE {
        cbQosTSCfgRate              Integer32,
        cbQosTSCfgBurstSize         Integer32,
        cbQosTSCfgExtBurstSize      Integer32,
        cbQosTSCfgAdaptiveEnabled   TruthValue,
        cbQosTSCfgAdaptiveRate      Integer32,
        cbQosTSCfgLimitType         TrafficShapingLimit,
        cbQosTSCfgRateType          CbQosRateType,
        cbQosTSCfgPercentRateValue  Unsigned32
}
 
cbQosTSCfgRate OBJECT-TYPE
        SYNTAX  Integer32 (8000..154400000)
        UNITS   "bits/second"
        MAX-ACCESS  read-only
        STATUS  current
        DESCRIPTION
                "The committed traffic-shaping rate.  This is the
                sustained rate permitted by the traffic-shaping."
 
        ::= { cbQosTSCfgEntry 1 }
 
cbQosTSCfgBurstSize OBJECT-TYPE
        SYNTAX  Integer32 (256..154400000)
        UNITS   "bits"
        MAX-ACCESS  read-only
        STATUS  current
        DESCRIPTION
                "The amount of traffic, in bits, in excess of the
                committed traffic-shaping rate that will be
                instantaneously permitted by this feature."
 
        ::= { cbQosTSCfgEntry 2 }
 
cbQosTSCfgExtBurstSize OBJECT-TYPE
        SYNTAX  Integer32 (0..154400000)
        UNITS   "bits"
        MAX-ACCESS  read-only
        STATUS  current
        DESCRIPTION
                "The amount of traffic, in bits, in excess of the
                burst limit, which may be conditionally permitted
                by traffic-shaping feature."
 
        ::= { cbQosTSCfgEntry 3 }
 
cbQosTSCfgAdaptiveEnabled OBJECT-TYPE
        SYNTAX  TruthValue
        MAX-ACCESS  read-only
        STATUS  current
        DESCRIPTION
                "This object indicates is adaptive traffic-shaping
                has been enabled."
 
        ::= { cbQosTSCfgEntry 4 }

cbQosTSCfgAdaptiveRate OBJECT-TYPE
        SYNTAX  Integer32 (8000..154400000)
        UNITS   "bits/second"
        MAX-ACCESS  read-only
        STATUS  current
        DESCRIPTION
                "This object represents the current adaptive traffic
                shaping rate."
 
        ::= { cbQosTSCfgEntry 5 }
 
cbQosTSCfgLimitType OBJECT-TYPE
        SYNTAX  TrafficShapingLimit
        MAX-ACCESS  read-only
        STATUS  current
        DESCRIPTION
                "This object indicates if traffic-shaping is limiting
                 traffic based on the peak rate or the average rate.
                "
        ::= { cbQosTSCfgEntry 6 }
 
cbQosTSCfgRateType OBJECT-TYPE
        SYNTAX  CbQosRateType 
        MAX-ACCESS  read-only
        STATUS  current
        DESCRIPTION
                "The rate type that configured for traffic-shaping.
                1 means rate is configured in bps.
                2 means rate is configured in percentage."

        ::= { cbQosTSCfgEntry 7 }

cbQosTSCfgPercentRateValue OBJECT-TYPE
        SYNTAX  Unsigned32 (0..100)
        UNITS   "% of Interface Bandwidth"
        MAX-ACCESS  read-only
        STATUS  current
        DESCRIPTION
                "The committed traffic-shaping rate in percentage.
                Its value is valid only when cbQosPoliceCfgRateType
                equals to 2."

        ::= { cbQosTSCfgEntry 8 }
-- end of cbQosTSCfgTable

-- The cbQosSetCfgObject group
--
-- cbQosSetCfg
 
cbQosSetCfgTable OBJECT-TYPE
        SYNTAX      SEQUENCE OF CbQosSetCfgEntry
        MAX-ACCESS  not-accessible
        STATUS      current
        DESCRIPTION
            "This table specifies Packet Marking Action configuration 
            information.
            "
        ::= { cbQosSetCfg 1 }
 
cbQosSetCfgEntry OBJECT-TYPE
        SYNTAX      CbQosSetCfgEntry
        MAX-ACCESS  not-accessible
        STATUS      current
        DESCRIPTION
           "Each entry in this table describes configuration information
           about a Packet Marking Action.  The table holds Packet
           Marking configuration parameters, such as type of packet
           marking and values being set to.

           This table contains configuration information only,
           no statistics associated with it. Therefore, it is indexed
           by the cbQosConfigIndex.
           "
        INDEX { cbQosConfigIndex }
        ::= { cbQosSetCfgTable 1 }
 
CbQosSetCfgEntry ::= SEQUENCE {
        cbQosSetCfgFeature           SetFeatureType,
        cbQosSetCfgIpDSCPValue       Integer32,
        cbQosSetCfgIpPrecedenceValue Integer32,
        cbQosSetCfgQosGroupValue     Integer32,
        cbQosSetCfgL2CosValue        Integer32,
        cbQosSetCfgMplsExpValue      Unsigned32,
        cbQosSetCfgDiscardClassValue Unsigned32,
        cbQosSetCfgMplsExpTopMostValue Unsigned32
}
 
cbQosSetCfgFeature OBJECT-TYPE
        SYNTAX  SetFeatureType
        MAX-ACCESS  read-only
        STATUS  current
        DESCRIPTION
               "The bit-wise position of each packet marking feature.
               "
        ::= { cbQosSetCfgEntry 1 }
 
cbQosSetCfgIpDSCPValue OBJECT-TYPE
        SYNTAX  Integer32 (0..63)
        MAX-ACCESS  read-only
        STATUS  current
        DESCRIPTION
                "The IP DSCP value at which the packet is being set 
                by the packet marking feature."
        ::= { cbQosSetCfgEntry 2 }

cbQosSetCfgIpPrecedenceValue OBJECT-TYPE
        SYNTAX  Integer32 (0..7)
        MAX-ACCESS  read-only
        STATUS  current
        DESCRIPTION
                "The IP precedence value at which the packet is being 
                set by the packet marking feature."
        ::= { cbQosSetCfgEntry 3 }

cbQosSetCfgQosGroupValue OBJECT-TYPE
        SYNTAX  Integer32 (0..99)
        MAX-ACCESS  read-only
        STATUS  current
        DESCRIPTION
                "The QoS Group number at which the packet is being 
                set by the packet marking feature."
        ::= { cbQosSetCfgEntry 4 }

cbQosSetCfgL2CosValue OBJECT-TYPE
        SYNTAX  Integer32 (0..7)
        MAX-ACCESS  read-only
        STATUS  current
        DESCRIPTION
                "The Layer 2 Cos value at which the packet is being 
                set by the packet marking feature."
        ::= { cbQosSetCfgEntry 5 }

cbQosSetCfgMplsExpValue OBJECT-TYPE
        SYNTAX  Unsigned32 (0..7)
        MAX-ACCESS  read-only
        STATUS  current
        DESCRIPTION
                "The MPLS experimental value at which the packet 
                is being set by the packet marking feature."
        ::= { cbQosSetCfgEntry 6 }

cbQosSetCfgDiscardClassValue OBJECT-TYPE
        SYNTAX  Unsigned32 (0..7)
        MAX-ACCESS  read-only
        STATUS  current
        DESCRIPTION
                "The Discard Class value at which the packet 
                is being set by the packet marking feature."
        ::= { cbQosSetCfgEntry 7 }

cbQosSetCfgMplsExpTopMostValue OBJECT-TYPE
        SYNTAX  Unsigned32 (0..7)
        MAX-ACCESS  read-only
        STATUS  current
        DESCRIPTION
                "The MPLS experimental value on the topmost label
                at which the packet is being set by the packet marking
                feature."

        ::= { cbQosSetCfgEntry 8 }

-- end of cbQosSetCfgTable
 


cbQosCMStatsTable OBJECT-TYPE
        SYNTAX      SEQUENCE OF CbQosCMStatsEntry
        MAX-ACCESS  not-accessible
        STATUS      current
        DESCRIPTION
            "This table specifies ClassMap related Statistical
            information.
            "
        ::= { cbQosClassMapStats 1 }

cbQosCMStatsEntry OBJECT-TYPE
        SYNTAX      CbQosCMStatsEntry 
        MAX-ACCESS  not-accessible
        STATUS      current
        DESCRIPTION
           "Each entry in this table describes the statistical 
           information about ClassMap. ClassMap specific information
           you can find in this table are : pre/post policy pkt/byte
           counts, bit rates, drop pkt/bytes and no buffer drops.

           This table contains statistical information only,
           no configuration information associated with it. Therefore, 
           it is indexed by the instance specific IDs, such as 
           cbQosPolicyIndex and cbQosObjectsIndex.
           "
        INDEX { cbQosPolicyIndex, cbQosObjectsIndex }
        ::= { cbQosCMStatsTable 1 }

CbQosCMStatsEntry ::= SEQUENCE {
        cbQosCMPrePolicyPktOverflow   Counter32,
        cbQosCMPrePolicyPkt           Counter32,
        cbQosCMPrePolicyPkt64         Counter64,
        cbQosCMPrePolicyByteOverflow  Counter32,
        cbQosCMPrePolicyByte          Counter32,
        cbQosCMPrePolicyByte64        Counter64,
        cbQosCMPrePolicyBitRate       Gauge32,
        cbQosCMPostPolicyByteOverflow Counter32,
        cbQosCMPostPolicyByte         Counter32,
        cbQosCMPostPolicyByte64       Counter64,
        cbQosCMPostPolicyBitRate      Gauge32,
        cbQosCMDropPktOverflow        Counter32,
        cbQosCMDropPkt                Counter32,
        cbQosCMDropPkt64              Counter64,
        cbQosCMDropByteOverflow       Counter32,
        cbQosCMDropByte               Counter32,
        cbQosCMDropByte64             Counter64,
        cbQosCMDropBitRate            Gauge32,
        cbQosCMNoBufDropPktOverflow   Counter32,
        cbQosCMNoBufDropPkt           Counter32,
        cbQosCMNoBufDropPkt64         Counter64
}


cbQosCMPrePolicyPktOverflow OBJECT-TYPE
        SYNTAX      Counter32
        MAX-ACCESS  read-only
        STATUS      current
        DESCRIPTION
             "The upper 32 bits count of inbound packets prior to 
             executing any QoS policies."
       ::= { cbQosCMStatsEntry 1 }

cbQosCMPrePolicyPkt OBJECT-TYPE
        SYNTAX      Counter32
        MAX-ACCESS  read-only
        STATUS      current
        DESCRIPTION
             "The lower 32 bits count of inbound packets prior to 
             executing any QoS policies."
       ::= { cbQosCMStatsEntry 2 }

cbQosCMPrePolicyPkt64 OBJECT-TYPE
        SYNTAX      Counter64
        MAX-ACCESS  read-only
        STATUS      current
        DESCRIPTION
             "The 64 bits count of inbound packets prior to executing 
             any QoS policies."
       ::= { cbQosCMStatsEntry 3 }

cbQosCMPrePolicyByteOverflow OBJECT-TYPE
        SYNTAX      Counter32
        MAX-ACCESS  read-only
        STATUS      current
        DESCRIPTION
             "The upper 32 bits count of inbound octets prior to 
             executing any QoS policies."
       ::= { cbQosCMStatsEntry 4 }

cbQosCMPrePolicyByte OBJECT-TYPE
        SYNTAX      Counter32
        MAX-ACCESS  read-only
        STATUS      current
        DESCRIPTION
             "The lower 32 bits count of inbound octets prior to 
             executing any QoS policies."
       ::= { cbQosCMStatsEntry 5 }

cbQosCMPrePolicyByte64 OBJECT-TYPE
        SYNTAX      Counter64
        MAX-ACCESS  read-only
        STATUS      current
        DESCRIPTION
             "The 64 bits count of inbound octets prior to executing 
             any QoS policies."
       ::= { cbQosCMStatsEntry 6 }

cbQosCMPrePolicyBitRate OBJECT-TYPE
        SYNTAX      Gauge32
        UNITS       "bits per second"
        MAX-ACCESS  read-only
        STATUS      current
        DESCRIPTION
               "The bit rate of the traffic prior to executing any QoS
                policies."
       ::= { cbQosCMStatsEntry 7 }

cbQosCMPostPolicyByteOverflow OBJECT-TYPE
        SYNTAX      Counter32
        MAX-ACCESS  read-only
        STATUS      current
        DESCRIPTION
             "The upper 32 bits count of outbound octets after executing
              QoS policies."
       ::= { cbQosCMStatsEntry 8 }

cbQosCMPostPolicyByte OBJECT-TYPE
        SYNTAX      Counter32
        MAX-ACCESS  read-only
        STATUS      current
        DESCRIPTION
             "The lower 32 bits count of outbound octets after executing
              QoS policies."
       ::= { cbQosCMStatsEntry 9 }

cbQosCMPostPolicyByte64 OBJECT-TYPE
        SYNTAX      Counter64
        MAX-ACCESS  read-only
        STATUS      current
        DESCRIPTION
             "The 64 bits count of outbound octets after executing 
              QoS policies."
       ::= { cbQosCMStatsEntry 10 }

cbQosCMPostPolicyBitRate OBJECT-TYPE
        SYNTAX      Gauge32
        UNITS       "bits per second"
        MAX-ACCESS  read-only
        STATUS      current
        DESCRIPTION
               "The bit rate of the traffic after executing QoS
                policies."
       ::= { cbQosCMStatsEntry 11 }

cbQosCMDropPktOverflow OBJECT-TYPE
        SYNTAX      Counter32
        MAX-ACCESS  read-only
        STATUS      current
        DESCRIPTION
               "The upper 32 bits counter of dropped pkts per class 
               as the result of all features that can produce drops 
               (e.g., police, random detect, etc.)."
       ::= { cbQosCMStatsEntry 12 }

cbQosCMDropPkt OBJECT-TYPE
        SYNTAX      Counter32
        MAX-ACCESS  read-only
        STATUS      current
        DESCRIPTION
               "The lower 32 bits counter of dropped pkts per class 
               as the result of all features that can produce drops 
               (e.g., police, random detect, etc.)."
       ::= { cbQosCMStatsEntry 13 }

cbQosCMDropPkt64 OBJECT-TYPE
        SYNTAX      Counter64
        MAX-ACCESS  read-only
        STATUS      current
        DESCRIPTION
               "The 64 bits counter of dropped pkts per class as 
               the result of all features that can produce drops 
                (e.g., police, random detect, etc.)."
       ::= { cbQosCMStatsEntry 14 }

cbQosCMDropByteOverflow OBJECT-TYPE
        SYNTAX      Counter32
        MAX-ACCESS  read-only
        STATUS      current
        DESCRIPTION
               "The upper 32 bits counter of dropped bytes per class 
               as the result of all features that can produce drops 
               (e.g., police, random detect, etc.)."
       ::= { cbQosCMStatsEntry 15 }

cbQosCMDropByte OBJECT-TYPE
        SYNTAX      Counter32
        MAX-ACCESS  read-only
        STATUS      current
        DESCRIPTION
               "The lower 32 bits counter of dropped bytes per class 
               as the result of all features that can produce drops 
               (e.g., police, random detect, etc.)."
       ::= { cbQosCMStatsEntry 16 }

cbQosCMDropByte64 OBJECT-TYPE
        SYNTAX      Counter64
        MAX-ACCESS  read-only
        STATUS      current
        DESCRIPTION
               "The 64 bits counter of dropped bytes per class as the 
               result of all features that can produce drops 
                (e.g., police, random detect, etc.)."
       ::= { cbQosCMStatsEntry 17 }

cbQosCMDropBitRate OBJECT-TYPE
        SYNTAX      Gauge32
        UNITS       "bits per second"
        MAX-ACCESS  read-only
        STATUS      current
        DESCRIPTION
               "The bit rate of the drops per class as the result of 
                all features that can produce drops 
                (e.g., police, random detect, etc.)."
       ::= { cbQosCMStatsEntry 18 }

cbQosCMNoBufDropPktOverflow OBJECT-TYPE
        SYNTAX      Counter32
        MAX-ACCESS  read-only
        STATUS      current
        DESCRIPTION
               "The upper 32 bits drop packet count which occured 
               due to a lack of SRAM buffers during output processing 
               on an interface."
       ::= { cbQosCMStatsEntry 19 }

cbQosCMNoBufDropPkt OBJECT-TYPE
        SYNTAX      Counter32
        MAX-ACCESS  read-only
        STATUS      current
        DESCRIPTION
               "The lower 32 bits drop packet count which occured due 
               to a lack of SRAM buffers during output processing on 
               an interface."
       ::= { cbQosCMStatsEntry 20 }

cbQosCMNoBufDropPkt64 OBJECT-TYPE
        SYNTAX      Counter64
        MAX-ACCESS  read-only
        STATUS      current
        DESCRIPTION
               "The 64 bits drop packet count which occured due to a 
               lack of SRAM buffers during output processing on an 
               interface."
       ::= { cbQosCMStatsEntry 21 }

--
-- End of cbQosCMStats group
--

--
-- QoS Match Statement Object Stats Table
--

cbQosMatchStmtStatsTable OBJECT-TYPE
        SYNTAX      SEQUENCE OF CbQosMatchStmtStatsEntry
        MAX-ACCESS  not-accessible
        STATUS      current
        DESCRIPTION
            "This table specifies Match Statement related statistical
            information.
            "
        ::= { cbQosMatchStmtStats 1 }

cbQosMatchStmtStatsEntry OBJECT-TYPE
        SYNTAX      CbQosMatchStmtStatsEntry
        MAX-ACCESS  not-accessible
        STATUS      current
        DESCRIPTION
           "Each entry in this table describes the statistical 
           information about Match Statement. Match Statement specific 
           information you can find in this table are : 
           Pre policy pkt/byte counters, and bit rates.

           This table contains statistical information only,
           no configuration information associated with it. Therefore, 
           it is indexed by the instance specific IDs, such as 
           cbQosPolicyIndex and cbQosObjectsIndex.
           "
        INDEX { cbQosPolicyIndex, cbQosObjectsIndex }
        ::= { cbQosMatchStmtStatsTable 1 }

CbQosMatchStmtStatsEntry ::= SEQUENCE {
        cbQosMatchPrePolicyPktOverflow   Counter32,
        cbQosMatchPrePolicyPkt           Counter32,
        cbQosMatchPrePolicyPkt64         Counter64,
        cbQosMatchPrePolicyByteOverflow  Counter32,
        cbQosMatchPrePolicyByte          Counter32,
        cbQosMatchPrePolicyByte64        Counter64,
        cbQosMatchPrePolicyBitRate       Gauge32
}

cbQosMatchPrePolicyPktOverflow OBJECT-TYPE
        SYNTAX      Counter32
        MAX-ACCESS  read-only
        STATUS      current
        DESCRIPTION
             "The upper 32 bits count of inbound packets prior to 
             executing any QoS policies."
       ::= { cbQosMatchStmtStatsEntry 1 }

cbQosMatchPrePolicyPkt OBJECT-TYPE
        SYNTAX      Counter32
        MAX-ACCESS  read-only
        STATUS      current
        DESCRIPTION
             "The lower 32 bits count of inbound packets prior to 
             executing any QoS policies."
       ::= { cbQosMatchStmtStatsEntry 2 }

cbQosMatchPrePolicyPkt64 OBJECT-TYPE
        SYNTAX      Counter64
        MAX-ACCESS  read-only
        STATUS      current
        DESCRIPTION
             "The 64 bits count of inbound packets prior to executing 
             any QoS policies."
       ::= { cbQosMatchStmtStatsEntry 3 }

cbQosMatchPrePolicyByteOverflow OBJECT-TYPE
        SYNTAX      Counter32
        MAX-ACCESS  read-only
        STATUS      current
        DESCRIPTION
             "The upper 32 bits count of inbound octets prior to 
             executing any QoS policies."
       ::= { cbQosMatchStmtStatsEntry 4 }

cbQosMatchPrePolicyByte OBJECT-TYPE
        SYNTAX      Counter32
        MAX-ACCESS  read-only
        STATUS      current
        DESCRIPTION
             "The lower 32 bits count of inbound octets prior to 
             executing any QoS policies."
       ::= { cbQosMatchStmtStatsEntry 5 }

cbQosMatchPrePolicyByte64 OBJECT-TYPE
        SYNTAX      Counter64
        MAX-ACCESS  read-only
        STATUS      current
        DESCRIPTION
             "The 64 bits count of inbound octets prior to executing 
             any QoS policies."
       ::= { cbQosMatchStmtStatsEntry 6 }

cbQosMatchPrePolicyBitRate OBJECT-TYPE
        SYNTAX      Gauge32
        UNITS       "bits per second"
        MAX-ACCESS  read-only
        STATUS      current
        DESCRIPTION
               "The bit rate of the traffic prior to executing any QoS
                policies."
       ::= { cbQosMatchStmtStatsEntry 7 }

--
-- The cbQosPoliceStats group 
--
-- cbQosPoliceStatsTable

cbQosPoliceStatsTable OBJECT-TYPE
        SYNTAX      SEQUENCE OF CbQosPoliceStatsEntry
        MAX-ACCESS  not-accessible
        STATUS      current
        DESCRIPTION
            "This table specifies Police Action related Statistical
            information.
            "
        ::= { cbQosPoliceStats 1 }

cbQosPoliceStatsEntry OBJECT-TYPE
        SYNTAX      CbQosPoliceStatsEntry
        MAX-ACCESS  not-accessible
        STATUS      current
        DESCRIPTION
           "Each entry in this table describes the statistical 
           information about Police Action. Police Action specific 
           information you can find in this table are : 
           Conformed/Exceeded pkt/byte counters,  bit rates.

           This table contains statistical information only,
           no configuration information associated with it. 
           Therefore, it is indexed by the instance specific IDs, 
           such as cbQosPolicyIndex and cbQosObjectsIndex.
           "
        INDEX { cbQosPolicyIndex, cbQosObjectsIndex }
        ::= { cbQosPoliceStatsTable 1 }

CbQosPoliceStatsEntry ::= SEQUENCE {
        cbQosPoliceConformedPktOverflow  Counter32,
        cbQosPoliceConformedPkt          Counter32,
        cbQosPoliceConformedPkt64        Counter64,
        cbQosPoliceConformedByteOverflow Counter32,
        cbQosPoliceConformedByte         Counter32,
        cbQosPoliceConformedByte64       Counter64,
        cbQosPoliceConformedBitRate      Gauge32,
        cbQosPoliceExceededPktOverflow   Counter32,
        cbQosPoliceExceededPkt           Counter32,
        cbQosPoliceExceededPkt64         Counter64,
        cbQosPoliceExceededByteOverflow  Counter32,
        cbQosPoliceExceededByte          Counter32,
        cbQosPoliceExceededByte64        Counter64,
        cbQosPoliceExceededBitRate       Gauge32,
        cbQosPoliceViolatedPktOverflow   Counter32,
        cbQosPoliceViolatedPkt           Counter32,
        cbQosPoliceViolatedPkt64         Counter64,
        cbQosPoliceViolatedByteOverflow  Counter32,
        cbQosPoliceViolatedByte          Counter32,
        cbQosPoliceViolatedByte64        Counter64,
        cbQosPoliceViolatedBitRate       Gauge32
}

cbQosPoliceConformedPktOverflow OBJECT-TYPE
        SYNTAX  Counter32
        UNITS   "Packets"
        MAX-ACCESS  read-only
        STATUS  current
        DESCRIPTION
                "The upper 32 bits count of packets treated as 
                conforming by the policing feature."
        ::= { cbQosPoliceStatsEntry 1 }

cbQosPoliceConformedPkt OBJECT-TYPE
        SYNTAX  Counter32
        UNITS   "Packets"
        MAX-ACCESS  read-only
        STATUS  current
        DESCRIPTION
                "The lower 32 bits count of packets treated as 
                conforming by the policing feature."
        ::= { cbQosPoliceStatsEntry 2 }

cbQosPoliceConformedPkt64 OBJECT-TYPE
        SYNTAX  Counter64
        UNITS   "Packets"
        MAX-ACCESS  read-only
        STATUS  current
        DESCRIPTION
                "The 64 bits count of packets treated as conforming 
                by the policing feature."
        ::= { cbQosPoliceStatsEntry 3 }

cbQosPoliceConformedByteOverflow OBJECT-TYPE
        SYNTAX  Counter32
        UNITS   "Octets"
        MAX-ACCESS  read-only
        STATUS  current
        DESCRIPTION
                "The upper 32 bits count of octets treated as 
                conforming by the policing feature."
        ::= { cbQosPoliceStatsEntry 4 }

cbQosPoliceConformedByte OBJECT-TYPE
        SYNTAX  Counter32
        UNITS   "Octets"
        MAX-ACCESS  read-only
        STATUS  current
        DESCRIPTION
                "The lower 32 bits count of octets treated as 
                conforming by the policing feature."
        ::= { cbQosPoliceStatsEntry 5 }

cbQosPoliceConformedByte64 OBJECT-TYPE
        SYNTAX  Counter64
        UNITS   "Octets"
        MAX-ACCESS  read-only
        STATUS  current
        DESCRIPTION
                "The 64 bits count of octets treated as conforming 
                by the policing feature."
        ::= { cbQosPoliceStatsEntry 6 }

cbQosPoliceConformedBitRate OBJECT-TYPE
        SYNTAX      Gauge32
        UNITS       "bits per second"
        MAX-ACCESS  read-only
        STATUS      current
        DESCRIPTION
                "The bit rate of conforming traffic."
        ::= { cbQosPoliceStatsEntry 7 }

cbQosPoliceExceededPktOverflow OBJECT-TYPE
        SYNTAX  Counter32
        UNITS   "Packets"
        MAX-ACCESS  read-only
        STATUS  current
        DESCRIPTION
                "The upper 32 bits count of packets treated as 
                non-conforming by the policing feature."

        ::= { cbQosPoliceStatsEntry 8 }

cbQosPoliceExceededPkt OBJECT-TYPE
        SYNTAX  Counter32
        UNITS   "Packets"
        MAX-ACCESS  read-only
        STATUS  current
        DESCRIPTION
                "The 32 bits count of packets treated as 
                non-conforming by the policing feature."

        ::= { cbQosPoliceStatsEntry 9 }

cbQosPoliceExceededPkt64 OBJECT-TYPE
        SYNTAX  Counter64
        UNITS   "Packets"
        MAX-ACCESS  read-only
        STATUS  current
        DESCRIPTION
                "The 64 bits count of packets treated as 
                non-conforming by the policing feature."

        ::= { cbQosPoliceStatsEntry 10 }

cbQosPoliceExceededByteOverflow OBJECT-TYPE
        SYNTAX  Counter32
        UNITS   "Octets"
        MAX-ACCESS  read-only
        STATUS  current
        DESCRIPTION
                "The upper 32 bits count of octets treated as 
                non-conforming by the policing feature."

        ::= { cbQosPoliceStatsEntry 11 }

cbQosPoliceExceededByte OBJECT-TYPE
        SYNTAX  Counter32
        UNITS   "Octets"
        MAX-ACCESS  read-only
        STATUS  current
        DESCRIPTION
                "The lower 32 bits count of octets treated as 
                non-conforming by the policing feature."

        ::= { cbQosPoliceStatsEntry 12 }

cbQosPoliceExceededByte64 OBJECT-TYPE
        SYNTAX  Counter64
        UNITS   "Octets"
        MAX-ACCESS  read-only
        STATUS  current
        DESCRIPTION
                "The 64 bits count of octets treated as 
                non-conforming by the policing feature."

        ::= { cbQosPoliceStatsEntry 13 }

cbQosPoliceExceededBitRate OBJECT-TYPE
        SYNTAX      Gauge32
        UNITS       "bits per second"
        MAX-ACCESS  read-only
        STATUS      current
        DESCRIPTION
                "The bit rate of the non-conforming traffic."

        ::= { cbQosPoliceStatsEntry 14 }

cbQosPoliceViolatedPktOverflow OBJECT-TYPE
        SYNTAX  Counter32
        UNITS   "Packets"
        MAX-ACCESS  read-only
        STATUS  current
        DESCRIPTION
                "The upper 32 bits count of packets treated as
              violated by the policing feature."

        ::= { cbQosPoliceStatsEntry 15 }

cbQosPoliceViolatedPkt OBJECT-TYPE
        SYNTAX  Counter32
        UNITS   "Packets"
        MAX-ACCESS  read-only
        STATUS  current
        DESCRIPTION
                "The 32 bits count of packets treated as
              violated by the policing feature."

        ::= { cbQosPoliceStatsEntry 16 }

cbQosPoliceViolatedPkt64 OBJECT-TYPE
        SYNTAX  Counter64
        UNITS   "Packets"
        MAX-ACCESS  read-only
        STATUS  current
        DESCRIPTION
                "The 64 bits count of packets treated as
              violated by the policing feature."

        ::= { cbQosPoliceStatsEntry 17 }

cbQosPoliceViolatedByteOverflow OBJECT-TYPE
        SYNTAX  Counter32
        UNITS   "Octets"
        MAX-ACCESS  read-only
        STATUS  current
        DESCRIPTION
                "The upper 32 bits count of octets treated as
              violated by the policing feature."

        ::= { cbQosPoliceStatsEntry 18 }

cbQosPoliceViolatedByte OBJECT-TYPE
        SYNTAX  Counter32
        UNITS   "Octets"
        MAX-ACCESS  read-only
        STATUS  current
        DESCRIPTION
                "The lower 32 bits count of octets treated as
              violated by the policing feature."

        ::= { cbQosPoliceStatsEntry 19 }

cbQosPoliceViolatedByte64 OBJECT-TYPE
        SYNTAX  Counter64
        UNITS   "Octets"
        MAX-ACCESS  read-only
        STATUS  current
        DESCRIPTION
                "The 64 bits count of octets treated as
              violated by the policing feature."

        ::= { cbQosPoliceStatsEntry 20 }

cbQosPoliceViolatedBitRate OBJECT-TYPE
        SYNTAX      Gauge32
        UNITS       "bits per second"
        MAX-ACCESS  read-only
        STATUS      current
        DESCRIPTION
                "The bit rate of the violating traffic."

        ::= { cbQosPoliceStatsEntry 21 }

-- end of cbQosPoliceStatsTable


--
-- The cbQosQueueingStats group
--
 
cbQosQueueingStatsTable OBJECT-TYPE
        SYNTAX      SEQUENCE OF CbQosQueueingStatsEntry
        MAX-ACCESS  not-accessible
        STATUS      current
        DESCRIPTION
            "This table specifies Queueing Action related Statistical
            information.
            "
        ::= { cbQosQueueingStats 1 }
 
cbQosQueueingStatsEntry OBJECT-TYPE
        SYNTAX      CbQosQueueingStatsEntry
        MAX-ACCESS  not-accessible
        STATUS      current
        DESCRIPTION
           "Each entry in this table describes the statistical 
           information about queueing action. Queueing action specific 
           information you can find in this table are : 
           various Q depth, and discard pkt/byte counters.

           This table contains statistical information only,
           no configuration information associated with it. 
           Therefore, it is indexed by the instance specific IDs, 
           such as cbQosPolicyIndex and cbQosObjectsIndex.
           "
        INDEX { cbQosPolicyIndex, cbQosObjectsIndex }
 
        ::= { cbQosQueueingStatsTable 1 }

 
CbQosQueueingStatsEntry ::= SEQUENCE {
        cbQosQueueingCurrentQDepth       Gauge32,
        cbQosQueueingMaxQDepth           Gauge32,
        cbQosQueueingDiscardByteOverflow Counter32,
        cbQosQueueingDiscardByte         Counter32,
        cbQosQueueingDiscardByte64       Counter64,
        cbQosQueueingDiscardPktOverflow  Counter32,
        cbQosQueueingDiscardPkt          Counter32,
        cbQosQueueingDiscardPkt64        Counter64
}
 
cbQosQueueingCurrentQDepth OBJECT-TYPE
        SYNTAX  Gauge32
        UNITS   "Octets"
        MAX-ACCESS  read-only
        STATUS  current
        DESCRIPTION
                "The current depth of the queue."

        ::= { cbQosQueueingStatsEntry 1 }

cbQosQueueingMaxQDepth OBJECT-TYPE
        SYNTAX  Gauge32
        UNITS   "Octets"
        MAX-ACCESS  read-only
        STATUS  current
        DESCRIPTION
                "The maximum depth of the queue."

        ::= { cbQosQueueingStatsEntry 2 }


cbQosQueueingDiscardByteOverflow OBJECT-TYPE
        SYNTAX  Counter32
        UNITS   "Octets"
        MAX-ACCESS  read-only
        STATUS  current
        DESCRIPTION
                "The upper 32 bit count of octets, associated with 
                this class, that were dropped by queueing."

        ::= { cbQosQueueingStatsEntry 3 }
 
cbQosQueueingDiscardByte OBJECT-TYPE
        SYNTAX  Counter32
        UNITS   "Octets"
        MAX-ACCESS  read-only
        STATUS  current
        DESCRIPTION
                "The lower 32 bits count of octets, associated with 
                this class, that were dropped by queueing."

        ::= { cbQosQueueingStatsEntry 4 }
 
cbQosQueueingDiscardByte64 OBJECT-TYPE
        SYNTAX  Counter64
        UNITS   "Octets"
        MAX-ACCESS  read-only
        STATUS  current
        DESCRIPTION
                "The count of octets, associated with this class,
                that were dropped by queueing."

        ::= { cbQosQueueingStatsEntry 5 }
 
cbQosQueueingDiscardPktOverflow OBJECT-TYPE
        SYNTAX  Counter32
        UNITS   "Packets"
        MAX-ACCESS  read-only
        STATUS  current
        DESCRIPTION
                "The upper 32 bits count of packets, associated with 
                this class, that were dropped by queueing."
 
        ::= { cbQosQueueingStatsEntry 6 }
 
cbQosQueueingDiscardPkt OBJECT-TYPE
        SYNTAX  Counter32
        UNITS   "Packets"
        MAX-ACCESS  read-only
        STATUS  current
        DESCRIPTION
                "The number of packets, associated with this class,
                that were dropped by queueing."
 
        ::= { cbQosQueueingStatsEntry 7 }
 
cbQosQueueingDiscardPkt64 OBJECT-TYPE
        SYNTAX  Counter64
        UNITS   "Packets"
        MAX-ACCESS  read-only
        STATUS  current
        DESCRIPTION
                "The number of packets, associated with this class,
                that were dropped by queueing."
 
        ::= { cbQosQueueingStatsEntry 8 }
 
-- end of cbQosQueueingStats Group

--
-- cbQosTSStats Group
--
 
cbQosTSStatsTable OBJECT-TYPE
        SYNTAX      SEQUENCE OF CbQosTSStatsEntry
        MAX-ACCESS  not-accessible
        STATUS      current
        DESCRIPTION
            "This table specifies traffic-shaping Action related 
            Statistical information.
            "
        ::= { cbQosTSStats 1 }
 
cbQosTSStatsEntry OBJECT-TYPE
        SYNTAX      CbQosTSStatsEntry
        MAX-ACCESS  not-accessible
        STATUS      current
        DESCRIPTION
           "Each entry in this table describes the statistical 
           information about traffic-shaping Action. Traffic-shaping 
           Action specific information you can find in this table are : 
           various delay/drop pkt/byte counters, state of feature,
           and Q size.

           This table contains statistical information only,
           no configuration information associated with it. 
           Therefore, it is indexed by the instance specific IDs, 
           such as cbQosPolicyIndex and cbQosObjectsIndex.
           "
        INDEX { cbQosPolicyIndex, cbQosObjectsIndex }
        ::= { cbQosTSStatsTable 1 }
 
CbQosTSStatsEntry ::= SEQUENCE {
        cbQosTSStatsDelayedByteOverflow  Counter32,
        cbQosTSStatsDelayedByte          Counter32,
        cbQosTSStatsDelayedByte64        Counter64,
        cbQosTSStatsDelayedPktOverflow   Counter32,
        cbQosTSStatsDelayedPkt           Counter32,
        cbQosTSStatsDelayedPkt64         Counter64,
        cbQosTSStatsDropByteOverflow     Counter32,
        cbQosTSStatsDropByte             Counter32,
        cbQosTSStatsDropByte64           Counter64,
        cbQosTSStatsDropPktOverflow      Counter32,
        cbQosTSStatsDropPkt              Counter32,
        cbQosTSStatsDropPkt64            Counter64,
        cbQosTSStatsActive               TruthValue,
        cbQosTSStatsCurrentQSize         Gauge32
}
 
 
cbQosTSStatsDelayedByteOverflow OBJECT-TYPE
        SYNTAX  Counter32
        UNITS   "octets"
        MAX-ACCESS  read-only
        STATUS  current
        DESCRIPTION
                "This object represents the upper 32 bits counter of 
                octets that have been delayed."
 
        ::= { cbQosTSStatsEntry 1 }

cbQosTSStatsDelayedByte OBJECT-TYPE
        SYNTAX  Counter32
        UNITS   "octets"
        MAX-ACCESS  read-only
        STATUS  current
        DESCRIPTION
                "This object represents the lower 32 bits counter of 
                octets that have been delayed."
 
        ::= { cbQosTSStatsEntry 2 }

cbQosTSStatsDelayedByte64 OBJECT-TYPE
        SYNTAX  Counter64
        UNITS   "octets"
        MAX-ACCESS  read-only
        STATUS  current
        DESCRIPTION
                "This object represents the 64 bits counter of 
                octets that have been delayed."
 
        ::= { cbQosTSStatsEntry 3 }

cbQosTSStatsDelayedPktOverflow OBJECT-TYPE
        SYNTAX  Counter32
        UNITS   "packets"
        MAX-ACCESS  read-only
        STATUS  current
        DESCRIPTION
                "This object represents the upper 32 bits counter of
                packets that have been delayed."
 
        ::= { cbQosTSStatsEntry 4 }
 
cbQosTSStatsDelayedPkt OBJECT-TYPE
        SYNTAX  Counter32
        UNITS   "packets"
        MAX-ACCESS  read-only
        STATUS  current
        DESCRIPTION
                "This object represents the lower 32 bits counter of
                packets that have been delayed."
 
        ::= { cbQosTSStatsEntry 5 }
 
cbQosTSStatsDelayedPkt64 OBJECT-TYPE
        SYNTAX  Counter64
        UNITS   "packets"
        MAX-ACCESS  read-only
        STATUS  current
        DESCRIPTION
                "This object represents the 64 bits counter of
                packets that have been delayed."
 
        ::= { cbQosTSStatsEntry 6 }
 
cbQosTSStatsDropByteOverflow OBJECT-TYPE
        SYNTAX  Counter32
        UNITS   "octets"
        MAX-ACCESS  read-only
        STATUS  current
        DESCRIPTION
                "This object represents the upper 32 bits counter of
                octets that have been dropped during shaping."
 
        ::= { cbQosTSStatsEntry 7 }
 
cbQosTSStatsDropByte OBJECT-TYPE
        SYNTAX  Counter32
        UNITS   "octets"
        MAX-ACCESS  read-only
        STATUS  current
        DESCRIPTION
                "This object represents the lower 32 bits counter of
                octets that have been dropped during shaping."
 
        ::= { cbQosTSStatsEntry 8 }
 
cbQosTSStatsDropByte64 OBJECT-TYPE
        SYNTAX  Counter64
        UNITS   "octets"
        MAX-ACCESS  read-only
        STATUS  current
        DESCRIPTION
                "This object represents the 64 bits counter of
                octets that have been dropped during shaping."
 
        ::= { cbQosTSStatsEntry 9 }
 
cbQosTSStatsDropPktOverflow OBJECT-TYPE
        SYNTAX  Counter32
        UNITS   "packets"
        MAX-ACCESS  read-only
        STATUS  current
        DESCRIPTION
                "This object represents the upper 32 bits counter of
                packets that have been dropped during shaping."
 
        ::= { cbQosTSStatsEntry 10 }

cbQosTSStatsDropPkt OBJECT-TYPE
        SYNTAX  Counter32
        UNITS   "packets"
        MAX-ACCESS  read-only
        STATUS  current
        DESCRIPTION
                "This object represents the lower 32 bits counter of
                packets that have been dropped during shaping."
 
        ::= { cbQosTSStatsEntry 11 }
 
cbQosTSStatsDropPkt64 OBJECT-TYPE
        SYNTAX  Counter64
        UNITS   "packets"
        MAX-ACCESS  read-only
        STATUS  current
        DESCRIPTION
                "This object represents the 64 bits counter of
                packets that have been dropped during shaping."
 
        ::= { cbQosTSStatsEntry 12 }
 
cbQosTSStatsActive OBJECT-TYPE
        SYNTAX  TruthValue
        MAX-ACCESS  read-only
        STATUS  current
        DESCRIPTION
                "This object indicates the current traffic-shaping
                state. When traffic-shaping is enabled and the traffic 
                rate exceeds the shape rate, traffic-shaping
                is considered to be active.  Otherwise, it is 
                considered inactive."
 
        ::= { cbQosTSStatsEntry 13 }
 
cbQosTSStatsCurrentQSize OBJECT-TYPE
        SYNTAX  Gauge32
        UNITS   "packets"
        MAX-ACCESS  read-only
        STATUS  current
        DESCRIPTION
                "This object indicates the current traffic-shaping
                queue depth in packets."
 
        ::= { cbQosTSStatsEntry 14 }
 
 
-- end of cbQosTSStats Group

--
-- cbQosREDClassStats Group
 
cbQosREDClassStatsTable OBJECT-TYPE
        SYNTAX      SEQUENCE OF CbQosREDClassStatsEntry
        MAX-ACCESS  not-accessible
        STATUS      current
        DESCRIPTION
            "This table specifies per Precedence WRED Action related 
            Statistical information.
            "
        ::= { cbQosREDClassStats 1 }
 
cbQosREDClassStatsEntry OBJECT-TYPE
        SYNTAX      CbQosREDClassStatsEntry
        MAX-ACCESS  not-accessible
        STATUS      current
        DESCRIPTION
           "Each entry in this table describes the statistical 
           information about per Precedence WRED Action. per Precedence
           WRED Action specific information you can find in this table 
           are : Random pkt/byte counters, and Tail drop pkt/byte 
           counters.

           This table contains per Precedence/dscp based statistical 
           information only, no configuration information associated 
           with it.  Therefore, it is indexed by the instance specific 
           IDs, and a per Precedence identifier: 
           cbQosPolicyIndex, cbQosObjectsIndex and cbQosREDValue.
           "
        INDEX { cbQosPolicyIndex, cbQosObjectsIndex, cbQosREDValue}
        ::= { cbQosREDClassStatsTable 1 }
 
CbQosREDClassStatsEntry ::= SEQUENCE {
        cbQosREDRandomDropPktOverflow  Counter32,
        cbQosREDRandomDropPkt          Counter32,
        cbQosREDRandomDropPkt64        Counter64,
        cbQosREDRandomDropByteOverflow Counter32,
        cbQosREDRandomDropByte         Counter32,
        cbQosREDRandomDropByte64       Counter64,
        cbQosREDTailDropPktOverflow    Counter32,
        cbQosREDTailDropPkt            Counter32,
        cbQosREDTailDropPkt64          Counter64,
        cbQosREDTailDropByteOverflow   Counter32,
        cbQosREDTailDropByte           Counter32,
        cbQosREDTailDropByte64         Counter64,
        cbQosREDTransmitPktOverflow    Counter32,
        cbQosREDTransmitPkt            Counter32,
        cbQosREDTransmitPkt64          Counter64,
        cbQosREDTransmitByteOverflow   Counter32,
        cbQosREDTransmitByte           Counter32,
        cbQosREDTransmitByte64         Counter64,
        cbQosREDECNMarkPktOverflow     Counter32,
        cbQosREDECNMarkPkt             Counter32,
        cbQosREDECNMarkPkt64           Counter64,
        cbQosREDECNMarkByteOverflow    Counter32,
        cbQosREDECNMarkByte            Counter32,
        cbQosREDECNMarkByte64          Counter64,
        cbQosREDMeanQSizeUnits         CbQosQueueUnitType,
        cbQosREDMeanQSize              CbQosQueueDepth
}
 
cbQosREDRandomDropPktOverflow OBJECT-TYPE
        SYNTAX  Counter32
        UNITS   "Packets"
        MAX-ACCESS  read-only
        STATUS  current
        DESCRIPTION
                "The upper 32 bits count of packets dropped when the 
                number of packets in the associated queue was greater
                than the minimum threshold and less than the
                maximum threshold."
 
        ::= { cbQosREDClassStatsEntry 1 }

cbQosREDRandomDropPkt OBJECT-TYPE
        SYNTAX  Counter32
        UNITS   "Packets"
        MAX-ACCESS  read-only
        STATUS  current
        DESCRIPTION
                "The lower 32 bits count of packets dropped when 
                the number of packets in the associated queue was 
                greater than the minimum threshold and less than the
                maximum threshold."
 
        ::= { cbQosREDClassStatsEntry 2 }

cbQosREDRandomDropPkt64 OBJECT-TYPE
        SYNTAX  Counter64
        UNITS   "Packets"
        MAX-ACCESS  read-only
        STATUS  current
        DESCRIPTION
                "The 64 bits count of packets dropped when the number 
                of packets in the associated queue was greater 
                than the minimum threshold and less than the
                maximum threshold."
 
        ::= { cbQosREDClassStatsEntry 3 }

cbQosREDRandomDropByteOverflow OBJECT-TYPE
        SYNTAX  Counter32
        UNITS   "Octets"
        MAX-ACCESS  read-only
        STATUS  current
        DESCRIPTION
                "The upper 32 bits count of bytes dropped when the 
                number of packets in the associated queue was greater
                than the minimum threshold and less than the
                maximum threshold."
 
        ::= { cbQosREDClassStatsEntry 4 }

cbQosREDRandomDropByte OBJECT-TYPE
        SYNTAX  Counter32
        UNITS   "Octets"
        MAX-ACCESS  read-only
        STATUS  current
        DESCRIPTION
                "The lower 32 bits count of bytes dropped when 
                the number of packets in the associated queue was 
                greater than the minimum threshold and less than the
                maximum threshold."
 
        ::= { cbQosREDClassStatsEntry 5 }

cbQosREDRandomDropByte64 OBJECT-TYPE
        SYNTAX  Counter64
        UNITS   "Octets"
        MAX-ACCESS  read-only
        STATUS  current
        DESCRIPTION
                "The 64 bits count of bytes dropped when the number of
                packets in the associated queue was greater
                than the minimum threshold and less than the
                maximum threshold."
 
        ::= { cbQosREDClassStatsEntry 6 }

cbQosREDTailDropPktOverflow OBJECT-TYPE
        SYNTAX  Counter32
        UNITS   "Packets"
        MAX-ACCESS  read-only
        STATUS  current
        DESCRIPTION
                "The upper 32 bits count of packets dropped when the 
                number of packets in the associated queue was greater
                than the maximum threshold."
 
        ::= { cbQosREDClassStatsEntry 7 }
 
cbQosREDTailDropPkt OBJECT-TYPE
        SYNTAX  Counter32
        UNITS   "Packets"
        MAX-ACCESS  read-only
        STATUS  current
        DESCRIPTION
                "The lower 32 bits count of packets dropped when the 
                number of packets in the associated queue was greater
                than the maximum threshold."
 
        ::= { cbQosREDClassStatsEntry 8 }
 
cbQosREDTailDropPkt64 OBJECT-TYPE
        SYNTAX  Counter64
        UNITS   "Packets"
        MAX-ACCESS  read-only
        STATUS  current
        DESCRIPTION
                "The 64 bits count of packets dropped when the number 
                of packets in the associated queue was greater
                than the maximum threshold."
 
        ::= { cbQosREDClassStatsEntry 9 }
 
cbQosREDTailDropByteOverflow OBJECT-TYPE
        SYNTAX  Counter32
        UNITS   "Octets"
        MAX-ACCESS  read-only
        STATUS  current
        DESCRIPTION
                "The upper 32 bits count of bytes dropped when the 
                number of packets in the associated queue was greater
                than the maximum threshold."
 
        ::= { cbQosREDClassStatsEntry 10 }
 
cbQosREDTailDropByte OBJECT-TYPE
        SYNTAX  Counter32
        UNITS   "Octets"
        MAX-ACCESS  read-only
        STATUS  current
        DESCRIPTION
                "The lower 32 bits count of bytes dropped when the 
                number of packets in the associated queue was greater
                than the maximum threshold."
 
        ::= { cbQosREDClassStatsEntry 11 }
 
cbQosREDTailDropByte64 OBJECT-TYPE
        SYNTAX  Counter64
        UNITS   "Octets"
        MAX-ACCESS  read-only
        STATUS  current
        DESCRIPTION
                "The 64 bits count of bytes dropped when the number of
                packets in the associated queue was greater
                than the maximum threshold."
 
        ::= { cbQosREDClassStatsEntry 12 }
 
cbQosREDTransmitPktOverflow OBJECT-TYPE
        SYNTAX  Counter32
        UNITS   "Packets"
        MAX-ACCESS  read-only
        STATUS  current
        DESCRIPTION
                "The upper 32 bits count of bytes transmitted."
 
        ::= { cbQosREDClassStatsEntry 13 }

cbQosREDTransmitPkt OBJECT-TYPE
        SYNTAX  Counter32
        UNITS   "Packets"
        MAX-ACCESS  read-only
        STATUS  current
        DESCRIPTION
                "The lower 32 bits count of bytes trasmitted."
 
        ::= { cbQosREDClassStatsEntry 14 }
 
cbQosREDTransmitPkt64 OBJECT-TYPE
        SYNTAX  Counter64
        UNITS   "Packets"
        MAX-ACCESS  read-only
        STATUS  current
        DESCRIPTION
                "The 64 bits count of packets transmitted."
 
        ::= { cbQosREDClassStatsEntry 15 }

cbQosREDTransmitByteOverflow OBJECT-TYPE
        SYNTAX  Counter32
        UNITS   "Octets"
        MAX-ACCESS  read-only
        STATUS  current
        DESCRIPTION
                "The upper 32 bits count of octets transmitted."
 
        ::= { cbQosREDClassStatsEntry 16 }

cbQosREDTransmitByte OBJECT-TYPE
        SYNTAX  Counter32
        UNITS   "Octets"
        MAX-ACCESS  read-only
        STATUS  current
        DESCRIPTION
                "The lower 32 bits count of octets trasmitted."
 
        ::= { cbQosREDClassStatsEntry 17 }
 
cbQosREDTransmitByte64 OBJECT-TYPE
        SYNTAX  Counter64
        UNITS   "Octets"
        MAX-ACCESS  read-only
        STATUS  current
        DESCRIPTION
                "The 64 bits count of octets transmitted."
 
        ::= { cbQosREDClassStatsEntry 18 }

cbQosREDECNMarkPktOverflow OBJECT-TYPE
        SYNTAX  Counter32
        UNITS   "Packets"
        MAX-ACCESS  read-only
        STATUS  current
        DESCRIPTION
                "The upper 32 bits count of packets ecn marked when the 
                number of packets in the associated queue was greater
                than the minimum threshold and less than the
                maximum threshold."
 
        ::= { cbQosREDClassStatsEntry 19 }

cbQosREDECNMarkPkt OBJECT-TYPE
        SYNTAX  Counter32
        UNITS   "Packets"
        MAX-ACCESS  read-only
        STATUS  current
        DESCRIPTION
                "The lower 32 bits count of packets ecn marked when 
                the number of packets in the associated queue was 
                greater than the minimum threshold and less than the
                maximum threshold."
 
        ::= { cbQosREDClassStatsEntry 20 }

cbQosREDECNMarkPkt64 OBJECT-TYPE
        SYNTAX  Counter64
        UNITS   "Packets"
        MAX-ACCESS  read-only
        STATUS  current
        DESCRIPTION
                "The 64 bits count of packets ecn marked when the 
                number of packets in the associated queue was 
                greater than the minimum threshold and less than 
                the maximum threshold."
 
        ::= { cbQosREDClassStatsEntry 21 }

cbQosREDECNMarkByteOverflow OBJECT-TYPE
        SYNTAX  Counter32
        UNITS   "Octets"
        MAX-ACCESS  read-only
        STATUS  current
        DESCRIPTION
                "The upper 32 bits count of bytes ecn marked when 
                the number of packets in the associated queue was 
                greater than the minimum threshold and less than the
                maximum threshold."
 
        ::= { cbQosREDClassStatsEntry 22 }

cbQosREDECNMarkByte OBJECT-TYPE
        SYNTAX  Counter32
        UNITS   "Octets"
        MAX-ACCESS  read-only
        STATUS  current
        DESCRIPTION
                "The lower 32 bits count of bytes ecn marked when 
                the number of packets in the associated queue was 
                greater than the minimum threshold and less than the
                maximum threshold."
 
        ::= { cbQosREDClassStatsEntry 23 }

cbQosREDECNMarkByte64 OBJECT-TYPE
        SYNTAX  Counter64
        UNITS   "Octets"
        MAX-ACCESS  read-only
        STATUS  current
        DESCRIPTION
                "The 64 bits count of bytes ecn marked when the 
                number of packets in the associated queue was 
                greater than the minimum threshold and less than the
                maximum threshold."
        
        ::= { cbQosREDClassStatsEntry 24 }

cbQosREDMeanQSizeUnits OBJECT-TYPE
        SYNTAX  CbQosQueueUnitType
        MAX-ACCESS  read-only
        STATUS  current
        DESCRIPTION
                "Represents the unit type of cbQosREDMeanQSize 
                object."
 
        ::= { cbQosREDClassStatsEntry 25 }

cbQosREDMeanQSize OBJECT-TYPE
        SYNTAX  CbQosQueueDepth
        MAX-ACCESS  read-only
        STATUS  current
        DESCRIPTION
                "The average queue size computed and used by the 
                WRED algorithm."
 
        ::= { cbQosREDClassStatsEntry 26 }

-- end of cbQosREDClassStatsTable

--
-- Start of cbQosIPHCCfgTable
--
cbQosIPHCCfgTable OBJECT-TYPE
        SYNTAX      SEQUENCE OF CbQosIPHCCfgEntry
        MAX-ACCESS  not-accessible
        STATUS      current
        DESCRIPTION
                "This table specifies IP Header Compression
                configuration information."
        ::= { cbQosIPHCCfg 1 }

cbQosIPHCCfgEntry OBJECT-TYPE
        SYNTAX      CbQosIPHCCfgEntry
        MAX-ACCESS  not-accessible
        STATUS      current
        DESCRIPTION
                "Each entry in this table describes configuration
                information about IP Header compression. This
                includes the compression option of UDP/RTP header,
                TCP header or both.

                This table contains configuration information only,
                no statistics associated with it. Therefore, it is
                indexed by cbQosConfigIndex."

        INDEX { cbQosConfigIndex }
        ::= { cbQosIPHCCfgTable 1 }

CbQosIPHCCfgEntry ::= SEQUENCE {
        cbQosIPHCCfgOption       IPHCOption
}

cbQosIPHCCfgOption OBJECT-TYPE
        SYNTAX  IPHCOption
        MAX-ACCESS  read-only
        STATUS  current
        DESCRIPTION
                "The configured IP header compression option.
                The value is defined by IPHCOption."

        ::= { cbQosIPHCCfgEntry 1 }

-- end of cbQosIPHCCfgTable

--
-- Start of cbQosIPHCStatsTable
--
cbQosIPHCStatsTable OBJECT-TYPE
        SYNTAX      SEQUENCE OF CbQosIPHCStatsEntry
        MAX-ACCESS  not-accessible
        STATUS      current
        DESCRIPTION
                "This table specifies IP Header Compression
                statistical information."
        ::= { cbQosIPHCStats 1 }

cbQosIPHCStatsEntry OBJECT-TYPE
        SYNTAX      CbQosIPHCStatsEntry
        MAX-ACCESS  not-accessible
        STATUS      current
        DESCRIPTION
                "Each entry in this table describes statistical
                information about IP Header compression.

                This table contains statistical information only,
                no configuration information associated with it.
                Therefore, it is indexed by the instance specific IDs,
                namely cbQosPolicyIndex and cbQosObjectsIndex."

        INDEX { cbQosPolicyIndex, cbQosObjectsIndex }
        ::= { cbQosIPHCStatsTable 1 }

CbQosIPHCStatsEntry ::= SEQUENCE {
        cbQosIPHCRtpSentPktOverflow      Counter32,
        cbQosIPHCRtpSentPkt              Counter32,
        cbQosIPHCRtpSentPkt64            Counter64,
        cbQosIPHCRtpCmprsOutPktOverflow  Counter32,
        cbQosIPHCRtpCmprsOutPkt          Counter32,
        cbQosIPHCRtpCmprsOutPkt64        Counter64,
        cbQosIPHCRtpSavedByteOverflow    Counter32,
        cbQosIPHCRtpSavedByte            Counter32,
        cbQosIPHCRtpSavedByte64          Counter64,
        cbQosIPHCRtpSentByteOverflow     Counter32,
        cbQosIPHCRtpSentByte             Counter32,
        cbQosIPHCRtpSentByte64           Counter64,
        cbQosIPHCRtpSentByteRate         Gauge32,
        cbQosIPHCTcpSentPktOverflow      Counter32,
        cbQosIPHCTcpSentPkt              Counter32,
        cbQosIPHCTcpSentPkt64            Counter64,
        cbQosIPHCTcpCmprsOutPktOverflow  Counter32,
        cbQosIPHCTcpCmprsOutPkt          Counter32,
        cbQosIPHCTcpCmprsOutPkt64        Counter64,
        cbQosIPHCTcpSavedByteOverflow    Counter32,
        cbQosIPHCTcpSavedByte            Counter32,
        cbQosIPHCTcpSavedByte64          Counter64,
        cbQosIPHCTcpSentByteOverflow     Counter32,
        cbQosIPHCTcpSentByte             Counter32,
        cbQosIPHCTcpSentByte64           Counter64,
        cbQosIPHCTcpSentByteRate         Gauge32
}

cbQosIPHCRtpSentPktOverflow OBJECT-TYPE
        SYNTAX      Counter32
        UNITS       "Packets"
        MAX-ACCESS  read-only
        STATUS      current
        DESCRIPTION
                "The upper 32 bits count of outbound UDP/RTP packets."
        ::= { cbQosIPHCStatsEntry 1 }

cbQosIPHCRtpSentPkt OBJECT-TYPE
        SYNTAX      Counter32
        UNITS       "Packets"
        MAX-ACCESS  read-only
        STATUS      current
        DESCRIPTION
                "The lower 32 bits count of outbound UDP/RTP packets."
        ::= { cbQosIPHCStatsEntry 2 }

cbQosIPHCRtpSentPkt64 OBJECT-TYPE
        SYNTAX      Counter64
        UNITS       "Packets"
        MAX-ACCESS  read-only
        STATUS      current
        DESCRIPTION
                "The 64 bits count of outbound UDP/RTP packets."
        ::= { cbQosIPHCStatsEntry 3 }

cbQosIPHCRtpCmprsOutPktOverflow OBJECT-TYPE
        SYNTAX      Counter32
        UNITS       "Packets"
        MAX-ACCESS  read-only
        STATUS      current
        DESCRIPTION
                "The upper 32 bits count of outbound compressed
                UDP/RTP packets."
        ::= { cbQosIPHCStatsEntry 4 }

cbQosIPHCRtpCmprsOutPkt OBJECT-TYPE
        SYNTAX      Counter32
        UNITS       "Packets"
        MAX-ACCESS  read-only
        STATUS      current
        DESCRIPTION
                "The lower 32 bits count of outbound compressed
                UDP/RTP packets."
        ::= { cbQosIPHCStatsEntry 5 }

cbQosIPHCRtpCmprsOutPkt64 OBJECT-TYPE
        SYNTAX      Counter64
        UNITS       "Packets"
        MAX-ACCESS  read-only
        STATUS      current
        DESCRIPTION
                "The 64 bits count of outbound compressed 
                UDP/RTP packets."
        ::= { cbQosIPHCStatsEntry 6 }

cbQosIPHCRtpSavedByteOverflow OBJECT-TYPE
        SYNTAX      Counter32
        UNITS       "Octets"
        MAX-ACCESS  read-only
        STATUS      current
        DESCRIPTION
                "The upper 32 bits count of UDP/RTP bytes that 
                saved due to IPHC."
        ::= { cbQosIPHCStatsEntry 7 }

cbQosIPHCRtpSavedByte OBJECT-TYPE
        SYNTAX      Counter32
        UNITS       "Octets"
        MAX-ACCESS  read-only
        STATUS      current
        DESCRIPTION
                "The lower 32 bits count of UDP/RTP bytes that 
                saved due to IPHC."
        ::= { cbQosIPHCStatsEntry 8 }

cbQosIPHCRtpSavedByte64 OBJECT-TYPE
        SYNTAX      Counter64
        UNITS       "Octets"
        MAX-ACCESS  read-only
        STATUS      current
        DESCRIPTION
                "The 64 bits count of UDP/RTP bytes that saved 
                due to IPHC."
        ::= { cbQosIPHCStatsEntry 9 }

cbQosIPHCRtpSentByteOverflow OBJECT-TYPE
        SYNTAX      Counter32
        UNITS       "Octets"
        MAX-ACCESS  read-only
        STATUS      current
        DESCRIPTION
                "The upper 32 bits count of outbound UDP/RTP 
                bytes."
        ::= { cbQosIPHCStatsEntry 10 }

cbQosIPHCRtpSentByte OBJECT-TYPE
        SYNTAX      Counter32
        UNITS       "Octets"
        MAX-ACCESS  read-only
        STATUS      current
        DESCRIPTION
                "The lower 32 bits count of outbound UDP/RTP 
                bytes."
        ::= { cbQosIPHCStatsEntry 11 }

cbQosIPHCRtpSentByte64 OBJECT-TYPE
        SYNTAX      Counter64
        UNITS       "Octets"
        MAX-ACCESS  read-only
        STATUS      current
        DESCRIPTION
                "The 64 bits count of outbound UDP/RTP bytes."
        ::= { cbQosIPHCStatsEntry 12 }

cbQosIPHCRtpSentByteRate OBJECT-TYPE
        SYNTAX      Gauge32 
        UNITS       "Octets per second"
        MAX-ACCESS  read-only
        STATUS      current
        DESCRIPTION
                "The 32 bits count of outbound UDP/RTP byte rate."
        ::= { cbQosIPHCStatsEntry 13 }

cbQosIPHCTcpSentPktOverflow OBJECT-TYPE
        SYNTAX      Counter32
        UNITS       "Packets"
        MAX-ACCESS  read-only
        STATUS      current
        DESCRIPTION
                "The upper 32 bits count of outbound TCP packets."
        ::= { cbQosIPHCStatsEntry 14 }

cbQosIPHCTcpSentPkt OBJECT-TYPE
        SYNTAX      Counter32
        UNITS       "Packets"
        MAX-ACCESS  read-only
        STATUS      current
        DESCRIPTION
                "The lower 32 bits count of outbound TCP packets."
        ::= { cbQosIPHCStatsEntry 15 }

cbQosIPHCTcpSentPkt64 OBJECT-TYPE
        SYNTAX      Counter64
        UNITS       "Packets"
        MAX-ACCESS  read-only
        STATUS      current
        DESCRIPTION
                "The 64 bits count of outbound TCP packets."
        ::= { cbQosIPHCStatsEntry 16 }

cbQosIPHCTcpCmprsOutPktOverflow OBJECT-TYPE
        SYNTAX      Counter32
        UNITS       "Packets"
        MAX-ACCESS  read-only
        STATUS      current
        DESCRIPTION
                "The upper 32 bits count of outbound compressed
                TCP packets."
        ::= { cbQosIPHCStatsEntry 17 }

cbQosIPHCTcpCmprsOutPkt OBJECT-TYPE
        SYNTAX      Counter32
        UNITS       "Packets"
        MAX-ACCESS  read-only
        STATUS      current
        DESCRIPTION
                "The lower 32 bits count of outbound compressed
                TCP packets."
        ::= { cbQosIPHCStatsEntry 18 }

cbQosIPHCTcpCmprsOutPkt64 OBJECT-TYPE
        SYNTAX      Counter64
        UNITS       "Packets"
        MAX-ACCESS  read-only
        STATUS      current
        DESCRIPTION
                "The 64 bits count of outbound compressed TCP
                packets."
        ::= { cbQosIPHCStatsEntry 19 }

cbQosIPHCTcpSavedByteOverflow OBJECT-TYPE
        SYNTAX      Counter32
        UNITS       "Octets"
        MAX-ACCESS  read-only
        STATUS      current
        DESCRIPTION
                "The upper 32 bits count of TCP bytes that saved
                due to IPHC."
        ::= { cbQosIPHCStatsEntry 20 }

cbQosIPHCTcpSavedByte OBJECT-TYPE
        SYNTAX      Counter32
        UNITS       "Octets"
        MAX-ACCESS  read-only
        STATUS      current
        DESCRIPTION
                "The lower 32 bits count of TCP bytes that saved
                due to IPHC."
        ::= { cbQosIPHCStatsEntry 21 }

cbQosIPHCTcpSavedByte64 OBJECT-TYPE
        SYNTAX      Counter64
        UNITS       "Octets"
        MAX-ACCESS  read-only
        STATUS      current
        DESCRIPTION
                "The 64 bits count of TCP bytes that saved due 
                to IPHC."
        ::= { cbQosIPHCStatsEntry 22 }

cbQosIPHCTcpSentByteOverflow OBJECT-TYPE
        SYNTAX      Counter32
        UNITS       "Octets"
        MAX-ACCESS  read-only
        STATUS      current
        DESCRIPTION
                "The upper 32 bits count of outbound TCP bytes."
        ::= { cbQosIPHCStatsEntry 23 }

cbQosIPHCTcpSentByte OBJECT-TYPE
        SYNTAX      Counter32
        UNITS       "Octets"
        MAX-ACCESS  read-only
        STATUS      current
        DESCRIPTION
                "The lower 32 bits count of outbound TCP bytes."
        ::= { cbQosIPHCStatsEntry 24 }

cbQosIPHCTcpSentByte64 OBJECT-TYPE
        SYNTAX      Counter64
        UNITS       "Octets"
        MAX-ACCESS  read-only
        STATUS      current
        DESCRIPTION
                "The 64 bits count of outbound TCP bytes."
        ::= { cbQosIPHCStatsEntry 25 }

cbQosIPHCTcpSentByteRate OBJECT-TYPE
        SYNTAX      Gauge32 
        UNITS       "Octets per second"
        MAX-ACCESS  read-only
        STATUS      current
        DESCRIPTION
                "The 32 bits count of outbound TCP byte rate."
        ::= { cbQosIPHCStatsEntry 26 }

-- end of cbQosIPHCStatsTable


ciscocbQosMIBCompliances  OBJECT IDENTIFIER 
                                ::= { ciscocbQosMIBConformance 1 }
ciscocbQosMIBGroups       OBJECT IDENTIFIER 
                                ::= { ciscocbQosMIBConformance 2 }

-- compliance statements

ciscocbQosMIBCompliance MODULE-COMPLIANCE
        STATUS       deprecated
        DESCRIPTION
            "The compliance statement for entities that implement 
            class-based QoS on a Cisco router."

        MODULE -- this module
        MANDATORY-GROUPS { 
                cbQosServicePolicyGroup,
                cbQosObjectsGroup,           
                cbQosPolicyMapCfgGroup,      
                cbQosClassMapCfgGroup,       
                cbQosMatchStmtCfgGroup,      
                cbQosQueueingCfgGroup,       
                cbQosREDCfgGroup,            
                cbQosREDClassCfgGroup,       
                cbQosPoliceCfgGroup,         
                cbQosTSCfgGroup,             
                cbQosSetCfgGroup,            
                cbQosClassMapStatsGroup,     
                cbQosMatchStmtStatsGroup,    
                cbQosPoliceStatsGroup,       
                cbQosQueueingStatsGroup,     
                cbQosTSStatsGroup,           
                cbQosREDClassStatsGroup     
        }

        GROUP   cbQosInterfacePolicyGroup
        DESCRIPTION
                "This is a optional group of information"

        GROUP   cbQosFrameRelayVCPolicyGroup
        DESCRIPTION
                "This is a optional group of information"

        GROUP   cbQosATMPVCPolicyGroup
        DESCRIPTION
                "This is a optional group of information"

        GROUP   cbQosNoBufferDropGroup 
        DESCRIPTION
                "This group is only available for code running on the 
                7500 platform."

        GROUP   cbQosQueueingDynamicQNumberGroup
        DESCRIPTION
                "This group is only available for code running on the
                7200 and/or lower platforms."

        GROUP   cbQosTrafficShapingDelayCountersGroup
        DESCRIPTION
                "This group is only available for code running on the
                7200 and/or lower platforms."

        ::= { ciscocbQosMIBCompliances 1 }

ciscocbQosMIBComplianceRev1 MODULE-COMPLIANCE
        STATUS      deprecated
        DESCRIPTION
            "The compliance statement for entities that implement 
            class-based QoS on a Cisco router. This compliance module
            deprecates ciscocbQosMIBCompliance."
  
        MODULE -- this module
        MANDATORY-GROUPS { 
                cbQosServicePolicyGroup,
                cbQosObjectsGroup,           
                cbQosPolicyMapCfgGroup,      
                cbQosClassMapCfgGroup,       
                cbQosMatchStmtCfgGroup,      
                cbQosQueueingCfgGroupRev1,       
                cbQosREDCfgGroupRev1,            
                cbQosREDClassCfgGroupRev1,       
                cbQosPoliceCfgGroupRev1,         
                cbQosTSCfgGroup,             
                cbQosSetCfgGroup,            
                cbQosClassMapStatsGroup,     
                cbQosMatchStmtStatsGroup,    
                cbQosPoliceStatsGroup,       
                cbQosQueueingStatsGroup,     
                cbQosTSStatsGroup,           
                cbQosREDClassStatsGroup 
        }

        GROUP   cbQosInterfacePolicyGroup
        DESCRIPTION
                "This is a optional group of information"

        GROUP   cbQosFrameRelayVCPolicyGroup
        DESCRIPTION
                "This is a optional group of information"

        GROUP   cbQosATMPVCPolicyGroup
        DESCRIPTION
                "This is a optional group of information"

        GROUP   cbQosNoBufferDropGroup 
        DESCRIPTION
                "This group is only available for code running on the 
                7500 platform."

        GROUP   cbQosQueueingDynamicQNumberGroup
        DESCRIPTION
                "This group is only available for code running on the
                7200 and/or lower platforms."

        GROUP   cbQosTrafficShapingDelayCountersGroup
        DESCRIPTION
                "This group is only available for code running on the
                7200 and/or lower platforms."

        ::= { ciscocbQosMIBCompliances 2 }

ciscocbQosMIBComplianceRev2 MODULE-COMPLIANCE
        STATUS      deprecated
        DESCRIPTION
            "The compliance statement for entities that implement
            class-based QoS on a Cisco router. This compliance module
            deprecates ciscocbQosMIBComplianceRev1."
  
        MODULE -- this module
        MANDATORY-GROUPS {
                cbQosServicePolicyGroup,
                cbQosObjectsGroup,
                cbQosPolicyMapCfgGroup,
                cbQosClassMapCfgGroup,
                cbQosMatchStmtCfgGroup,
                cbQosQueueingCfgGroupRev1,
                cbQosREDCfgGroupRev1,
                cbQosREDClassCfgGroupRev1,
                cbQosPoliceCfgGroupRev2,
                cbQosTSCfgGroup,
                cbQosSetCfgGroupRev1,
                cbQosClassMapStatsGroup,
                cbQosMatchStmtStatsGroup,
                cbQosPoliceStatsGroup,
                cbQosQueueingStatsGroup,
                cbQosTSStatsGroup,
                cbQosREDClassStatsGroup
        }

        GROUP   cbQosInterfacePolicyGroup
        DESCRIPTION
                "This is a optional group of information"

        GROUP   cbQosFrameRelayVCPolicyGroup
        DESCRIPTION
                "This is a optional group of information"

        GROUP   cbQosATMPVCPolicyGroup
        DESCRIPTION
                "This is a optional group of information"

        GROUP   cbQosNoBufferDropGroup
        DESCRIPTION
                "This group is only available for code running on the
                7500 platform."

        GROUP   cbQosQueueingDynamicQNumberGroup
        DESCRIPTION
                "This group is only available for code running on the
                7200 and/or lower platforms."

        GROUP   cbQosREDClassXmitCountersGroup
        DESCRIPTION
                "This group is only available on platforms that
                supporting WRED transmit stats."

        GROUP   cbQosREDECNCfgGroup
        DESCRIPTION
                "This group is only available on platforms that
                supporting WRED ECN configuration."

        GROUP   cbQosREDClassECNMarkCountersGroup
        DESCRIPTION
                "This group is only available on platforms that
                supporting WRED ECN stats."

        GROUP   cbQosAFPoliceStatsGroup
        DESCRIPTION
                "This group is only available on platforms that
                supporting POLICE violate action stats."

        GROUP   cbQosPoliceCfgPirGroup
        DESCRIPTION
                "This group is only available on platforms that
                supporting police PIR configuration."

        GROUP   cbQosPoliceCfgExtGroup
        DESCRIPTION
                "This group is only available for code running on the
                Catalyst 4000 platform."

        GROUP   cbQosPoliceActionCfgGroup
        DESCRIPTION
                "This group is only available on platforms that
                supporting multiple POLICE conform/exceed actions."

        GROUP   cbQosAFPoliceViolateCfgGroup
        DESCRIPTION
                "This group is only available on platforms that
                supporting multiple POLICE violate actions."

        GROUP   cbQosPoliceCfgPercentGroup
        DESCRIPTION
                "This group is only available on platforms that
                supporting police CIR/PIR in percentage."

        GROUP   cbQosTrafficShapingDelayCountersGroup
        DESCRIPTION
                "This group is only available for code running on the
                7200 and/or lower platforms."

        GROUP   cbQosTSCfgPercentGroup
        DESCRIPTION
                "This group is only available on platforms that
                supporting committed shaping rate in percentage."

        GROUP   cbQosNewSetCfgGroup
        DESCRIPTION
                "This group is only available on platforms that
                supporting SET L2 Cos config."

        GROUP   cbQosSetCfgMplsImpositionGroup 
        DESCRIPTION
                "This group is only available on platforms that
                supporting SET MPLS Experimental Imposition config."

        GROUP   cbQosSetCfgDiscardClassGroup
        DESCRIPTION
                "This group is only available on platforms that
                supporting SET Discard Class config."

        GROUP   cbQosSetCfgMPLSTopMostGroup 
        DESCRIPTION
                "This group is only available on platforms that
                supporting SET MPLS Experimental Top Most config."

        GROUP   cbQosIPHCCfgGroup
        DESCRIPTION
                "This group is only available on platforms that
                supporting IPHC configuration."

        GROUP   cbQosIPHCStatsGroup
        DESCRIPTION
                "This group is only available on platforms that
                supporting IPHC stats."

        ::= { ciscocbQosMIBCompliances 3 }

-- units of conformance

ciscocbQosMIBComplianceRev3 MODULE-COMPLIANCE
        STATUS      current
        DESCRIPTION
            "The compliance statement for entities that implement
            class-based QoS on a Cisco router. This compliance module
            deprecates ciscocbQosMIBComplianceRev2."
  
        MODULE -- this module
        MANDATORY-GROUPS {
                cbQosServicePolicyGroupRev1,
                cbQosObjectsGroup,
                cbQosPolicyMapCfgGroup,
                cbQosClassMapCfgGroup,
                cbQosMatchStmtCfgGroup,
                cbQosQueueingCfgGroupRev1,
                cbQosREDDscpCfgGroup,
                cbQosREDCfgGroupRev1,
                cbQosREDClassCfgGroupRev1,
                cbQosPoliceCfgGroupRev2,
                cbQosTSCfgGroup,
                cbQosSetCfgGroupRev1,
                cbQosClassMapStatsGroup,
                cbQosMatchStmtStatsGroup,
                cbQosPoliceStatsGroup,
                cbQosQueueingStatsGroup,
                cbQosTSStatsGroup,
                cbQosREDClassStatsGroup
        }

        GROUP   cbQosInterfacePolicyGroup
        DESCRIPTION
                "This is a optional group of information"

        GROUP   cbQosFrameRelayVCPolicyGroup
        DESCRIPTION
                "This is a optional group of information"

        GROUP   cbQosATMPVCPolicyGroup
        DESCRIPTION
                "This is a optional group of information"

        GROUP   cbQosNoBufferDropGroup
        DESCRIPTION
                "This group is only available for code running on the
                7500 platform."

        GROUP   cbQosQueueingDynamicQNumberGroup
        DESCRIPTION
                "This group is only available for code running on the
                7200 and/or lower platforms."

        GROUP   cbQosREDClassXmitCountersGroup
        DESCRIPTION
                "This group is only available on platforms that
                supporting WRED transmit stats."

        GROUP   cbQosREDECNCfgGroup
        DESCRIPTION
                "This group is only available on platforms that
                supporting WRED ECN configuration."

        GROUP   cbQosREDClassECNMarkCountersGroup
        DESCRIPTION
                "This group is only available on platforms that
                supporting WRED ECN stats."

        GROUP   cbQosAFPoliceStatsGroup
        DESCRIPTION
                "This group is only available on platforms that
                supporting POLICE violate action stats."

        GROUP   cbQosPoliceCfgPirGroup
        DESCRIPTION
                "This group is only available on platforms that
                supporting police PIR configuration."

        GROUP   cbQosPoliceCfgExtGroup
        DESCRIPTION
                "This group is only available for code running on the
                Catalyst 4000 platform."

        GROUP   cbQosPoliceActionCfgGroup
        DESCRIPTION
                "This group is only available on platforms that
                supporting multiple POLICE conform/exceed actions."

        GROUP   cbQosAFPoliceViolateCfgGroup
        DESCRIPTION
                "This group is only available on platforms that
                supporting multiple POLICE violate actions."

        GROUP   cbQosPoliceCfgPercentGroup
        DESCRIPTION
                "This group is only available on platforms that
                supporting police CIR/PIR in percentage."

        GROUP   cbQosTrafficShapingDelayCountersGroup
        DESCRIPTION
                "This group is only available for code running on the
                7200 and/or lower platforms."

        GROUP   cbQosTSCfgPercentGroup
        DESCRIPTION
                "This group is only available on platforms that
                supporting committed shaping rate in percentage."

        GROUP   cbQosNewSetCfgGroup
        DESCRIPTION
                "This group is only available on platforms that
                supporting SET L2 Cos config."

        GROUP   cbQosSetCfgMplsImpositionGroup 
        DESCRIPTION
                "This group is only available on platforms that
                supporting SET MPLS Experimental Imposition config."

        GROUP   cbQosSetCfgDiscardClassGroup
        DESCRIPTION
                "This group is only available on platforms that
                supporting SET Discard Class config."

        GROUP   cbQosSetCfgMPLSTopMostGroup 
        DESCRIPTION
                "This group is only available on platforms that
                supporting SET MPLS Experimental Top Most config."

        GROUP   cbQosIPHCCfgGroup
        DESCRIPTION
                "This group is only available on platforms that
                supporting IPHC configuration."

        GROUP   cbQosIPHCStatsGroup
        DESCRIPTION
                "This group is only available on platforms that
                supporting IPHC stats."

        ::= { ciscocbQosMIBCompliances 4 }

-- units of conformance

cbQosServicePolicyGroup OBJECT-GROUP
        OBJECTS {
                cbQosIfType,
                cbQosPolicyDirection,
                cbQosIfIndex,
                cbQosFrDLCI,
                cbQosAtmVPI,
                cbQosAtmVCI
        }
        STATUS      deprecated
        DESCRIPTION
            "Required objects to provide CB QoS objects configuration 
             information."
        ::= { ciscocbQosMIBGroups 1 }

cbQosInterfacePolicyGroup   OBJECT-GROUP
        OBJECTS {
                cbQosIFPolicyIndex
        }
        STATUS      current
        DESCRIPTION
            "Required objects to provide CB QoS objects configuration 
             information."
        ::= { ciscocbQosMIBGroups 2 }

cbQosFrameRelayVCPolicyGroup OBJECT-GROUP
        OBJECTS {
                cbQosFRPolicyIndex
        }
        STATUS      current
        DESCRIPTION
            "Required objects to provide CB QoS objects configuration 
             information."
        ::= { ciscocbQosMIBGroups 3 }

cbQosATMPVCPolicyGroup      OBJECT-GROUP
        OBJECTS {
                cbQosATMPolicyIndex
        }
        STATUS      current
        DESCRIPTION
            "Required objects to provide CB QoS objects configuration 
             information."
        ::= { ciscocbQosMIBGroups 4 }

cbQosObjectsGroup           OBJECT-GROUP
        OBJECTS {
                cbQosConfigIndex,
                cbQosObjectsType,
                cbQosParentObjectsIndex
        }
        STATUS      current
        DESCRIPTION
            "Required objects to provide CB QoS objects configuration 
             information."
        ::= { ciscocbQosMIBGroups 5 }

cbQosPolicyMapCfgGroup      OBJECT-GROUP
        OBJECTS {
                cbQosPolicyMapName,
                cbQosPolicyMapDesc
        }
        STATUS      current
        DESCRIPTION
            "Required objects to provide CB QoS objects configuration 
             information."
        ::= { ciscocbQosMIBGroups 6 }

cbQosClassMapCfgGroup       OBJECT-GROUP
        OBJECTS {
                cbQosCMName,
                cbQosCMDesc,
                cbQosCMInfo
        }
        STATUS      current
        DESCRIPTION
            "Required objects to provide CB QoS objects configuration 
             information."
        ::= { ciscocbQosMIBGroups 7 }

cbQosMatchStmtCfgGroup      OBJECT-GROUP
        OBJECTS {
                cbQosMatchStmtName,
                cbQosMatchStmtInfo
        }
        STATUS      current
        DESCRIPTION
            "Required objects to provide CB QoS objects configuration 
             information."
        ::= { ciscocbQosMIBGroups 8 }

cbQosQueueingCfgGroup       OBJECT-GROUP
        OBJECTS {
                cbQosQueueingCfgBandwidth,
                cbQosQueueingCfgBandwidthUnits,
                cbQosQueueingCfgFlowEnabled,
                cbQosQueueingCfgPriorityEnabled,
                cbQosQueueingCfgAggregateQSize,
                cbQosQueueingCfgIndividualQSize,
                cbQosQueueingCfgPrioBurstSize
        }
        STATUS   deprecated -- superceded by cbQosQueueingCfgGroupRev1
        DESCRIPTION
            "Required objects to provide CB QoS objects configuration 
             information."
        ::= { ciscocbQosMIBGroups 9 }

cbQosREDCfgGroup            OBJECT-GROUP
        OBJECTS {
                cbQosREDCfgExponWeight,
                cbQosREDCfgMeanQsize
        }
        STATUS      deprecated -- superceded by cbQosREDCfgGroupRev1 
        DESCRIPTION
            "Required objects to provide CB QoS objects configuration 
             information."
        ::= { ciscocbQosMIBGroups 10 }

cbQosREDClassCfgGroup       OBJECT-GROUP
        OBJECTS {
                cbQosREDCfgMinThreshold,
                cbQosREDCfgMaxThreshold,
                cbQosREDCfgPktDropProb
        }
        STATUS   deprecated -- superceded by cbQosREDClassCfgGroupRev1
        DESCRIPTION
            "Required objects to provide CB QoS objects configuration 
             information."
        ::= { ciscocbQosMIBGroups 11 }

cbQosPoliceCfgGroup         OBJECT-GROUP
        OBJECTS {
                cbQosPoliceCfgRate,
                cbQosPoliceCfgBurstSize,
                cbQosPoliceCfgExtBurstSize,
                cbQosPoliceCfgConformAction,
                cbQosPoliceCfgConformSetValue,
                cbQosPoliceCfgExceedAction,
                cbQosPoliceCfgExceedSetValue,
                cbQosPoliceCfgPir
        }
        STATUS     deprecated -- superceded by cbQosPoliceCfgGroupRev1
        DESCRIPTION
            "Required objects to provide CB QoS objects configuration 
             information."
        ::= { ciscocbQosMIBGroups 12 }

cbQosTSCfgGroup             OBJECT-GROUP
        OBJECTS {
                cbQosTSCfgRate,
                cbQosTSCfgBurstSize,
                cbQosTSCfgExtBurstSize,
                cbQosTSCfgAdaptiveEnabled,
                cbQosTSCfgAdaptiveRate,
                cbQosTSCfgLimitType
        }
        STATUS      current
        DESCRIPTION
            "Required objects to provide CB QoS objects configuration 
             information."
        ::= { ciscocbQosMIBGroups 13 }

cbQosSetCfgGroup            OBJECT-GROUP
        OBJECTS {
                cbQosSetCfgFeature,
                cbQosSetCfgIpDSCPValue,
                cbQosSetCfgIpPrecedenceValue,
                cbQosSetCfgQosGroupValue,
                cbQosSetCfgL2CosValue,
                cbQosSetCfgMplsExpValue,
                cbQosSetCfgDiscardClassValue
        }
        STATUS      deprecated -- superceded by cbQosSetCfgGroupRev1 
        DESCRIPTION
            "Required objects to provide CB QoS objects configuration 
             information."
        ::= { ciscocbQosMIBGroups 14 }

cbQosClassMapStatsGroup     OBJECT-GROUP
        OBJECTS {
                cbQosCMPrePolicyPktOverflow,
                cbQosCMPrePolicyPkt,
                cbQosCMPrePolicyPkt64,
                cbQosCMPrePolicyByteOverflow,
                cbQosCMPrePolicyByte,
                cbQosCMPrePolicyByte64,
                cbQosCMPrePolicyBitRate,
                cbQosCMPostPolicyByteOverflow,
                cbQosCMPostPolicyByte,
                cbQosCMPostPolicyByte64,
                cbQosCMPostPolicyBitRate,
                cbQosCMDropPktOverflow,
                cbQosCMDropPkt,
                cbQosCMDropPkt64,
                cbQosCMDropByteOverflow,
                cbQosCMDropByte,
                cbQosCMDropByte64,
                cbQosCMDropBitRate
        }
        STATUS      current
        DESCRIPTION
            "Required objects to provide CB QoS objects configuration 
             information."
        ::= { ciscocbQosMIBGroups 15 }

cbQosNoBufferDropGroup OBJECT-GROUP
        OBJECTS {
                cbQosCMNoBufDropPktOverflow,
                cbQosCMNoBufDropPkt,
                cbQosCMNoBufDropPkt64         
        }
        STATUS      current
        DESCRIPTION
            "Optional objects to provide CB QoS summary statistics."
        ::= { ciscocbQosMIBGroups 16 }

cbQosQueueingDynamicQNumberGroup OBJECT-GROUP
        OBJECTS {
                cbQosQueueingCfgDynamicQNumber
        }
        STATUS      current
        DESCRIPTION
            "Optional objects to provide CB QoS Queueing information."
        ::= { ciscocbQosMIBGroups 17 }

cbQosTrafficShapingDelayCountersGroup OBJECT-GROUP
        OBJECTS {
            cbQosTSStatsDelayedByteOverflow,
            cbQosTSStatsDelayedByte,
            cbQosTSStatsDelayedByte64,
            cbQosTSStatsDelayedPktOverflow,
            cbQosTSStatsDelayedPkt,
            cbQosTSStatsDelayedPkt64,
            cbQosTSStatsActive
        }
        STATUS      current
        DESCRIPTION
            "Optional objects to provide CB QoS traffic-shaping 
            information."
        ::= { ciscocbQosMIBGroups 18 }

cbQosMatchStmtStatsGroup    OBJECT-GROUP
        OBJECTS {
                cbQosMatchPrePolicyPktOverflow,
                cbQosMatchPrePolicyPkt,
                cbQosMatchPrePolicyPkt64,
                cbQosMatchPrePolicyByteOverflow,
                cbQosMatchPrePolicyByte,
                cbQosMatchPrePolicyByte64,
                cbQosMatchPrePolicyBitRate
        }
        STATUS      current
        DESCRIPTION
            "Required objects to provide CB QoS objects configuration 
             information."
        ::= { ciscocbQosMIBGroups 19 }

cbQosPoliceStatsGroup       OBJECT-GROUP
        OBJECTS {
                cbQosPoliceConformedPktOverflow,
                cbQosPoliceConformedPkt,
                cbQosPoliceConformedPkt64,
                cbQosPoliceConformedByteOverflow,
                cbQosPoliceConformedByte,
                cbQosPoliceConformedByte64,
                cbQosPoliceConformedBitRate,
                cbQosPoliceExceededPktOverflow,
                cbQosPoliceExceededPkt,
                cbQosPoliceExceededPkt64,
                cbQosPoliceExceededByteOverflow,
                cbQosPoliceExceededByte,
                cbQosPoliceExceededByte64,
                cbQosPoliceExceededBitRate
        }
        STATUS      current
        DESCRIPTION
            "Required objects to provide CB QoS objects configuration 
             information."
        ::= { ciscocbQosMIBGroups 20 }

cbQosQueueingStatsGroup     OBJECT-GROUP
        OBJECTS {
                cbQosQueueingCurrentQDepth,
                cbQosQueueingMaxQDepth,
                cbQosQueueingDiscardByteOverflow,
                cbQosQueueingDiscardByte,
                cbQosQueueingDiscardByte64,
                cbQosQueueingDiscardPktOverflow,
                cbQosQueueingDiscardPkt,
                cbQosQueueingDiscardPkt64
        }
        STATUS      current
        DESCRIPTION
            "Required objects to provide CB QoS objects configuration 
             information."
        ::= { ciscocbQosMIBGroups 21 }

cbQosTSStatsGroup           OBJECT-GROUP
        OBJECTS {
                cbQosTSStatsDropByteOverflow,
                cbQosTSStatsDropByte,
                cbQosTSStatsDropByte64,
                cbQosTSStatsDropPktOverflow,
                cbQosTSStatsDropPkt,
                cbQosTSStatsDropPkt64,
                cbQosTSStatsCurrentQSize
        }
        STATUS      current
        DESCRIPTION
            "Required objects to provide CB QoS objects configuration 
             information."
        ::= { ciscocbQosMIBGroups 22 }

cbQosREDClassStatsGroup     OBJECT-GROUP
        OBJECTS {
                cbQosREDRandomDropPktOverflow,
                cbQosREDRandomDropPkt,
                cbQosREDRandomDropPkt64,
                cbQosREDRandomDropByteOverflow,
                cbQosREDRandomDropByte,
                cbQosREDRandomDropByte64,
                cbQosREDTailDropPktOverflow,
                cbQosREDTailDropPkt,
                cbQosREDTailDropPkt64,
                cbQosREDTailDropByteOverflow,
                cbQosREDTailDropByte,
                cbQosREDTailDropByte64,
                cbQosREDMeanQSizeUnits,
                cbQosREDMeanQSize
        }
        STATUS      current
        DESCRIPTION
            "Required objects to provide CB QoS objects configuration 
             information."
        ::= { ciscocbQosMIBGroups 23 }

cbQosREDClassXmitCountersGroup     OBJECT-GROUP
        OBJECTS {
                cbQosREDTransmitPktOverflow,
                cbQosREDTransmitPkt,
                cbQosREDTransmitPkt64,
                cbQosREDTransmitByteOverflow,
                cbQosREDTransmitByte,
                cbQosREDTransmitByte64
        }
        STATUS      current
        DESCRIPTION
            "Optional objects to provide CB QoS objects configuration 
             information."
        ::= { ciscocbQosMIBGroups 24 }

cbQosAFPoliceStatsGroup       OBJECT-GROUP
        OBJECTS {
              cbQosPoliceViolatedPktOverflow,
              cbQosPoliceViolatedPkt,
              cbQosPoliceViolatedPkt64,
              cbQosPoliceViolatedByteOverflow,
              cbQosPoliceViolatedByte,
              cbQosPoliceViolatedByte64,
              cbQosPoliceViolatedBitRate
        }
        STATUS      current
        DESCRIPTION
            "Optional objects to provide CB QoS objects configuration
             information."
        ::= { ciscocbQosMIBGroups 25 }

cbQosAFPoliceCfgGroup         OBJECT-GROUP
        OBJECTS {
              cbQosPoliceCfgViolateAction,
              cbQosPoliceCfgViolateSetValue
        }
        STATUS      deprecated
        DESCRIPTION
            "Optional objects to provide CB QoS objects configuration
             information."
        ::= { ciscocbQosMIBGroups 26 }

cbQosREDDscpCfgGroup         OBJECT-GROUP
        OBJECTS {
              cbQosREDCfgDscpPrec
        }
        STATUS      current
        DESCRIPTION
            "Required objects to provide CB QoS objects configuration
             information."
        ::= { ciscocbQosMIBGroups 27 }

cbQosNewSetCfgGroup         OBJECT-GROUP
        OBJECTS {
              cbQosSetCfgL2CosValue
        }
        STATUS      current
        DESCRIPTION
            "Optional objects to provide CB QoS objects configuration
             information."
        ::= { ciscocbQosMIBGroups 28 }

cbQosQueueingCfgGroupRev1       OBJECT-GROUP
        OBJECTS {
                cbQosQueueingCfgBandwidth,
                cbQosQueueingCfgBandwidthUnits,
                cbQosQueueingCfgFlowEnabled,
                cbQosQueueingCfgPriorityEnabled,
                cbQosQueueingCfgIndividualQSize,
                cbQosQueueingCfgPrioBurstSize,
                cbQosQueueingCfgQLimitUnits,
                cbQosQueueingCfgAggregateQLimit
        }
        STATUS      current
        DESCRIPTION
            "Required objects to provide CB QoS objects configuration 
            information."
        ::= { ciscocbQosMIBGroups 29 }

cbQosREDCfgGroupRev1            OBJECT-GROUP
        OBJECTS {
                cbQosREDCfgExponWeight
        }
        STATUS      current
        DESCRIPTION
            "Required objects to provide CB QoS objects configuration 
            information."
        ::= { ciscocbQosMIBGroups 30 }

cbQosREDClassCfgGroupRev1       OBJECT-GROUP
        OBJECTS {
                cbQosREDCfgPktDropProb,
                cbQosREDClassCfgThresholdUnit,
                cbQosREDClassCfgMinThreshold,
                cbQosREDClassCfgMaxThreshold
        }
        STATUS      current
        DESCRIPTION
            "Required objects to provide CB QoS objects configuration 
            information."
        ::= { ciscocbQosMIBGroups 31 }

cbQosPoliceCfgGroupRev1         OBJECT-GROUP
        OBJECTS {
                cbQosPoliceCfgRate,
                cbQosPoliceCfgBurstSize,
                cbQosPoliceCfgExtBurstSize,
                cbQosPoliceCfgPir
        }
        STATUS      deprecated -- superceded by cbQosPoliceCfgGroupRev2
                               -- and cbQosPoliceCfgPirGroup
        DESCRIPTION
            "Required objects to provide CB QoS objects configuration 
             information."
        ::= { ciscocbQosMIBGroups 32 }

cbQosPoliceActionCfgGroup         OBJECT-GROUP
        OBJECTS {
                cbQosPoliceActionCfgConform,
                cbQosPoliceActionCfgConformSetValue,
                cbQosPoliceActionCfgExceed,
                cbQosPoliceActionCfgExceedSetValue
        }
        STATUS      current
        DESCRIPTION
            "Required objects to provide CB QoS objects configuration 
             information."
        ::= { ciscocbQosMIBGroups 33 }

cbQosAFPoliceViolateCfgGroup         OBJECT-GROUP
        OBJECTS {
              cbQosPoliceActionCfgViolate,
              cbQosPoliceActionCfgViolateSetValue
        }
        STATUS      current
        DESCRIPTION
            "Optional objects to provide CB QoS objects configuration
             information."
        ::= { ciscocbQosMIBGroups 34 }

cbQosREDECNCfgGroup         OBJECT-GROUP
        OBJECTS {
                cbQosREDCfgECNEnabled
        }
        STATUS      current
        DESCRIPTION
            "Optional objects to provide CB QoS objects configuration
             information."
        ::= { ciscocbQosMIBGroups 35 }

cbQosREDClassECNMarkCountersGroup     OBJECT-GROUP
        OBJECTS {
                cbQosREDECNMarkPktOverflow,
                cbQosREDECNMarkPkt,
                cbQosREDECNMarkPkt64,
                cbQosREDECNMarkByteOverflow,
                cbQosREDECNMarkByte,
                cbQosREDECNMarkByte64
        }
        STATUS      current
        DESCRIPTION
            "Optional objects to provide CB QoS objects configuration 
             information."
        ::= { ciscocbQosMIBGroups 36 }

cbQosPoliceCfgExtGroup         OBJECT-GROUP
        OBJECTS {
                cbQosPoliceCfgRate64
        }
        STATUS      current
        DESCRIPTION
            "Optional objects to provide the information of the
             committed policing rate that is greater than the
             maximum value reportable by cbQosPoliceCfgRate."
        ::= { ciscocbQosMIBGroups 37 }

cbQosSetCfgGroupRev1            OBJECT-GROUP
        OBJECTS {
                cbQosSetCfgFeature,
                cbQosSetCfgIpDSCPValue,
                cbQosSetCfgIpPrecedenceValue,
                cbQosSetCfgQosGroupValue
        }
        STATUS      current
        DESCRIPTION
            "Required objects to provide CB QoS objects configuration 
             information for SET/Marking feature."
        ::= { ciscocbQosMIBGroups 38 }

cbQosSetCfgMplsImpositionGroup            OBJECT-GROUP
        OBJECTS {
                cbQosSetCfgMplsExpValue
        }
        STATUS      current
        DESCRIPTION
            "Optional object to provide CB QoS objects configuration 
             information for SET/Marking feature."
        ::= { ciscocbQosMIBGroups 39 }

cbQosSetCfgDiscardClassGroup            OBJECT-GROUP
        OBJECTS {
                cbQosSetCfgDiscardClassValue
        }
        STATUS      current
        DESCRIPTION
            "Optional object to provide CB QoS objects configuration 
             information for SET/Marking feature."
        ::= { ciscocbQosMIBGroups 40 }

cbQosSetCfgMPLSTopMostGroup            OBJECT-GROUP
        OBJECTS {
                cbQosSetCfgMplsExpTopMostValue
        }
        STATUS      current
        DESCRIPTION
            "Optional object to provide CB QoS objects configuration 
             information for SET/Marking feature."
        ::= { ciscocbQosMIBGroups 41 }

cbQosPoliceCfgGroupRev2         OBJECT-GROUP
        OBJECTS {
                cbQosPoliceCfgRate,
                cbQosPoliceCfgBurstSize,
                cbQosPoliceCfgExtBurstSize
        }
        STATUS      current
        DESCRIPTION
            "Required objects to provide CB QoS objects configuration 
             information for POLICE feature."
        ::= { ciscocbQosMIBGroups 42 }

cbQosPoliceCfgPirGroup         OBJECT-GROUP
        OBJECTS {
                cbQosPoliceCfgPir
        }
        STATUS      current
        DESCRIPTION
            "Optional objects to provide CB QoS policing PIR rate." 
        ::= { ciscocbQosMIBGroups 43 }

cbQosPoliceCfgPercentGroup         OBJECT-GROUP
        OBJECTS {
                cbQosPoliceCfgRateType,
                cbQosPoliceCfgPercentRateValue,
                cbQosPoliceCfgPercentPirValue
        }
        STATUS      current
        DESCRIPTION
            "Optional objects to provide CB QoS policing CIR and PIR 
             rates in percentage."
        ::= { ciscocbQosMIBGroups 44 }

cbQosTSCfgPercentGroup         OBJECT-GROUP
        OBJECTS {
                cbQosTSCfgRateType,
                cbQosTSCfgPercentRateValue
        }
        STATUS      current
        DESCRIPTION
            "Optional objects to provide CB QoS committed 
             traffic-shaping rate in percentage."
        ::= { ciscocbQosMIBGroups 45 }

cbQosIPHCCfgGroup         OBJECT-GROUP
        OBJECTS {
                cbQosIPHCCfgOption
        }
        STATUS      current
        DESCRIPTION
            "Optional object to provide CB QoS IP header compression
             configuration information."
        ::= { ciscocbQosMIBGroups 46 }

cbQosIPHCStatsGroup         OBJECT-GROUP
        OBJECTS {
                cbQosIPHCRtpSentPktOverflow,
                cbQosIPHCRtpSentPkt,
                cbQosIPHCRtpSentPkt64,
                cbQosIPHCRtpCmprsOutPktOverflow,
                cbQosIPHCRtpCmprsOutPkt,
                cbQosIPHCRtpCmprsOutPkt64,
                cbQosIPHCRtpSavedByteOverflow,
                cbQosIPHCRtpSavedByte,
                cbQosIPHCRtpSavedByte64,
                cbQosIPHCRtpSentByteOverflow,
                cbQosIPHCRtpSentByte,
                cbQosIPHCRtpSentByte64,
                cbQosIPHCRtpSentByteRate,
                cbQosIPHCTcpSentPktOverflow,
                cbQosIPHCTcpSentPkt,
                cbQosIPHCTcpSentPkt64,
                cbQosIPHCTcpCmprsOutPktOverflow,
                cbQosIPHCTcpCmprsOutPkt,
                cbQosIPHCTcpCmprsOutPkt64,
                cbQosIPHCTcpSavedByteOverflow,
                cbQosIPHCTcpSavedByte,
                cbQosIPHCTcpSavedByte64,
                cbQosIPHCTcpSentByteOverflow,
                cbQosIPHCTcpSentByte,
                cbQosIPHCTcpSentByte64,
                cbQosIPHCTcpSentByteRate
        }
        STATUS      current
        DESCRIPTION
            "Optional objects to provide CB QoS IP header compression
             statistic information."
        ::= { ciscocbQosMIBGroups 47 }

cbQosServicePolicyGroupRev1 OBJECT-GROUP
        OBJECTS {
                cbQosIfType,
                cbQosPolicyDirection,
                cbQosIfIndex,
                cbQosFrDLCI,
                cbQosAtmVPI,
                cbQosAtmVCI,
                cbQosEntityIndex
        }
        STATUS      current
        DESCRIPTION
            "Required objects to provide CB QoS objects configuration 
             information. This group deprecates 
             cbQosServicePolicyGroup."
        ::= { ciscocbQosMIBGroups 48 }

END
