SCM-MIB DEFINITIONS ::= BEGIN



IMPORTS
	OBJECT-TYPE, NOTIFICATION-TYPE,Unsigned32
		FROM SNMPv2-SMI
		TruthValue,TEXTUAL-CONVENTION
		FROM SNMPv2-TC
		 MODULE-IDENTITY, OBJECT-TYPE, Integer32,
    Unsigned32, NOTIFICATION-TYPE
        FROM SNMPv2-SMI                  -- RFC2578
        switch    
 		FROM PRVT-SWITCH-MIB;   

scmMib MODULE-IDENTITY
        LAST-UPDATED "200801010000Z"
        ORGANIZATION "BATM Advanced Communication"
        CONTACT-INFO
        " BATM/Telco Systems Support team
				Email: 
				For North America: techsupport@telco.com
				For North Europe: support@batm.de, info@batm.de
				For the rest of the world: techsupport@telco.com"

        DESCRIPTION
        "This module includes configuration parameters for DS1 modules not included in 
        DS1-MIB."            
        REVISION     "200801010000Z"
     	 DESCRIPTION
		"Removed redefined OIDs in private vendor extension definitions." 

        REVISION     "200603070000Z"
     	 	DESCRIPTION
					"Added an additional port index to the alarm table."

        REVISION     "200602230000Z"
     	 	DESCRIPTION
						"Added the TCA alarms table objects and the TCA alarm trap."
        REVISION     "200503110000Z"
     	 DESCRIPTION
		"Initial version."    
        ::= { switch 499 }

sysClkMgr OBJECT IDENTIFIER ::= { scmMib 1 }

clkMgrOpts OBJECT IDENTIFIER ::= { sysClkMgr 1 }
clkInputs OBJECT IDENTIFIER ::= { sysClkMgr 2 }
clkOutputs OBJECT IDENTIFIER ::= { sysClkMgr 3 }
clkMgrAlarms OBJECT IDENTIFIER ::= { sysClkMgr 4 }

  
-- ----------------------------------------------------------------------------
-- Variable Type definitions
-- ----------------------------------------------------------------------------
T1CableLength ::= TEXTUAL-CONVENTION
STATUS current
DESCRIPTION
"This value is used to configure T1 long cable length."
SYNTAX INTEGER {
notApplicable (0), 
t1-133ft (1),
t1-266ft  (2),
t1-399ft (3),
t1-533ft (4),
t1-655ft  (5),
neg15dB (6),
neg225dB (7),      
neg75dB (8)
}    

E1CableImpedance ::= TEXTUAL-CONVENTION
STATUS current
DESCRIPTION
"This value is used to configure E1 impedance."
SYNTAX INTEGER { 
notApplicable(0),
e1-75ohm(1),   
e1-120ohm(2),
t1-75ohm (3),
t1-100ohm(4)
}


shelfId OBJECT-TYPE
	SYNTAX INTEGER (1..254)
	MAX-ACCESS read-only
	STATUS current
	DESCRIPTION
	"ShelfId indicates logical number of the shelf where Master 
	Clock Generator is located. The value for this object is 
	obtained from IPMC as part of SCM initialization. Currently 
	only shelfId 1..9 is expected to be in use but the range is 
	defined to be valid also for future bigger instalations."
	::= { clkMgrOpts 1 }

slotId OBJECT-TYPE
	SYNTAX INTEGER
	{
		slot8 (1),
		slot9 (2)
	}
	MAX-ACCESS read-only
	STATUS current
	DESCRIPTION
	"slotId indicates physical number of slot in the specific 
	shelf where MCG is located. The value for this object is 
	obtained from IPMC as part of SCM initialization."
	::= { clkMgrOpts 2 }

mcgOperationMode OBJECT-TYPE
	SYNTAX INTEGER
	{
		main      (1),
		redundant (2),
		test      (3),
		separate  (4),
		not-applicable(5)
	}
	MAX-ACCESS read-write
	STATUS current
	DESCRIPTION
	"MCG operating mode of entity may have following values: 
	main (active), redundant (passive), test (intended to be 
	used for testing,  sending clock signals is restricted, 
	currently not supported by AHUB1-A) or separate (unit is 
	not in use, sending clock signals is prohibited). Reading
	object returns current operation mode, writing forces MCG 
	into new operation mode. This object is initialized to the 
	output of the HW arbiter after Initialization (see arbiter 
	section for more details).
	The value of not applicable is read-only. It occurs when  
	the RTM is not connected."
	::= { clkMgrOpts 3 }

mcgFunction OBJECT-TYPE
	SYNTAX INTEGER
	{
		mcg1 (1),
		mcg2 (2)
	}
	MAX-ACCESS read-write
	STATUS current
	DESCRIPTION
	"MCG function determines whether MCG should act as MCG1 or 
	MCG2. The initial value for this object is MCG1 if shelfId 
	is 1 and MCG2 Otherwise."
	::= { clkMgrOpts 4 }

refSwitchMode OBJECT-TYPE
	SYNTAX INTEGER
	{
		revertive     (1),
		non-revertive (2)
	}
	MAX-ACCESS read-write
	STATUS current
	DESCRIPTION
	"Reference Switching Mode (revertive, non-revertive) 
	Determines whether or not MCG is allowed to revert back 
	using recovered reference clock input."
	::= { clkMgrOpts 5 }

pllAdministrativeMode OBJECT-TYPE
	SYNTAX INTEGER
	{
		synchronized (1),
		hold-over    (2),
		free-run     (3)
	}   
	MAX-ACCESS read-write
	STATUS current
	DESCRIPTION
	"PLL administative mode (synchronized, hold-over, free-run) 
	Indicates the operation mode requested by the SM. Operation
mode can be forced as free-run by setting this object. 
Forcing hold-over is only valid if operational mode is 
synchronized. Default value for this object is 
synchronized."
	::= { clkMgrOpts 6 }

pllOperationMode OBJECT-TYPE
	SYNTAX INTEGER
	{
		synchronized (1),
		hold-over    (2),
		free-run     (3),
		locking      (4),
		not-applicable(5)
	}   
	MAX-ACCESS read-only
	STATUS current
	DESCRIPTION
	"PLL operation mode (synchronized, hold-over, free-run) 
	Indicates the current operation mode of MCG's internal 
	oscillator. Upon initialization, if there is a valid source 
	then this will be set to synchronized as soon as 
	synchronization achieved, otherwise it will be set to free-
	run.
	The value of not-applicable occurs when the RTM is not 
	connected."
	::= { clkMgrOpts 7 }

pllControlWord OBJECT-TYPE
	SYNTAX INTEGER  (-2147483648..2147483647)
	MAX-ACCESS read-write
	STATUS current
	DESCRIPTION
	"PLL control word may be used for adjusting system clock 
	frequency in free-run operation mode. MAX VALUE DEPENDS 
	RANGE OF USED D/A CONVERTER."
	::= { clkMgrOpts 8 }

calibrateFreq OBJECT-TYPE
	SYNTAX INTEGER
	{
		idle-done (1),
		activate  (2)
	}
	MAX-ACCESS read-write
	STATUS current
	DESCRIPTION
	"CalibrateFreq once assigned with value activate(2) shall 
	Initialize the frequency calibration. During calibration 
	mean value of PLL control word over short period is written
to non-volatile memory and calibrateFreq is assigned with 
id/done(1) value to indicate accomplishment of calibration. 
PLL control word written in memory is actually only non-
static variable that should be saved to last over system 
boot. PLL control word is recovered from non-volatile 
memory at system power up and used as factory default value 
for system clock frequency in free-run operation mode. PLL 
Control Word shall be middle value of control word range if 
no calibration has been performed."
	::= { clkMgrOpts 9 }

faultAnalysisControl OBJECT-TYPE
	SYNTAX INTEGER
	{
		idle-done (1),
		activate  (2)
	} 
	MAX-ACCESS read-write
	STATUS current
	DESCRIPTION
	"faultAnalysisControl once assigned with value activate(2) 
	shall Initialize fault analysis. Once analysis is completed 
	and result is available in faultAnalysisResult object, 
	value of Control object is changed to idle/done(1) to 
	indicate accomplishment of analysis."
	::= { clkMgrOpts 10 }

faultAnalysisResult OBJECT-TYPE
	SYNTAX INTEGER
	{
		systemOk (1),
		pldFailure (2),
		synchronizationUnitFailure (4),
		framerFailure (8)
	}
	MAX-ACCESS read-only
	STATUS current
	DESCRIPTION
	"FaultAnalysisResult contains result of fault analysis.
Possible return values in addition to system_ok are failures
in HW components in the RTM."
	::= { clkMgrOpts 11 }

systemEvents OBJECT-TYPE
	SYNTAX OCTET STRING
	MAX-ACCESS read-only
	STATUS current
	DESCRIPTION
	"SystemEvents contains dedicated bits for indicating some 
	Special conditions in system. Same information may be 
	obtained by detecting related traps (notifications) or by 
	polling this register (if trap reception is not supported 
	in SNMP Agent). Value of object may be also combination of 
	any defined values. Upon a GET request, this object is 
	clearned once the reply has been sent
	entityUp               	('10000000 00000000'),
	pllOperationModeChange 	('01000000 00000000'B),
	mcgOperationModeChange 	('00100000 00000000'B),
	clkInputUp             	('00010000 00000000'B),
	clkInputDown           	('00001000 00000000'B),
	hardwareError          	('00000100 00000000'B),
	pllHoldOverAlarm       	('00000010 00000000'B),
	extInputSSMChanged	('00000001 00000000'B)
	"
	::= { clkMgrOpts 12 }

errorType OBJECT-TYPE
	SYNTAX OCTET STRING

	MAX-ACCESS read-only
	STATUS current
	DESCRIPTION
	"Error type determines reason for HW related error.
	Value of object may be also combination of any defined 
	values.
	systemClockNotOscillating			('10000000'B),
	extBitsOutputLOS          			('01000000'B), -- MCG1 only 
	mcg1FrequencyOutOfRange   			('00100000'B),-- MCG2 only
	mainMcgFrequencyOutOfRange 			('00010000'B),-- redundant MCGs only
	artm1ABoardIsAbsent     			('00001000'B)"
	::= { clkMgrOpts 13 }

upAndRunning OBJECT-TYPE
	SYNTAX Unsigned32 (0..4294967295)
	MAX-ACCESS read-write
	STATUS current
	DESCRIPTION
	"This integer type object is used for detecting managed 
	entity is still up and running, moreover that it is able to 
	process given command. Managed entity must automatically 
	increment value written into object with decimal number 1 
	(one). If value 1 is written and object value is read 
	result must be 2. It is required that incrementing this 
	variable will be performed by the SCM's main task to ensure 
	its sanity."
	::= { clkMgrOpts 14 }

squelch OBJECT-TYPE
	SYNTAX INTEGER
	{
		enabled  (1),
		disabled (2)
	}   
	MAX-ACCESS read-write
	STATUS current
	DESCRIPTION
"If squelch is enabled, if a reference fails, Tx of framer is automatically disabled. If it's disabled - the Tx of the framer is not autimatically disabled."
	::= { clkMgrOpts 15 }

pllTimingMode OBJECT-TYPE
	SYNTAX INTEGER
	{
		stratum3  (1),
		sec       (2)
	}   
	MAX-ACCESS read-write
	STATUS current
	DESCRIPTION
" Pll Timing Mode (stratum 3 | SEC) indicates the timing mode requested by the SM. "
	::= { clkMgrOpts 16 }





inputPriorityListTable OBJECT-TYPE
	SYNTAX SEQUENCE OF InputPriorityListEntry
	MAX-ACCESS not-accessible
	STATUS current
	DESCRIPTION
	"A table containing the priority list for reference inputs. 
	Priority list contains preferred order when several 
	reference clocks are available. Object controls Select B in 
	Figure A. A reference source with no priority assigned 
	cannot be used. Keeping this list empty is another way to 
	force free-run mode.
Upon initialization, MCG1 expects to receive reference clock through EXT/BITS#1, and the table should look:	
clkInputId	clkInputPriority
1	1
MCG2 expects to receive system clock through CHILD(UP)/CHILD(DOWN) connectors.
clkInputId	clkInputPriority
9	1
"
	::= { clkInputs 1 }

inputPriorityListEntry OBJECT-TYPE
	SYNTAX InputPriorityListEntry
	MAX-ACCESS not-accessible
	STATUS current
	DESCRIPTION
		""
    INDEX  { clkInputId }
	::= { inputPriorityListTable 1 }

InputPriorityListEntry ::= SEQUENCE {
	clkInputId			INTEGER,
	clkInputPriority	INTEGER
	}

clkInputId OBJECT-TYPE
	SYNTAX INTEGER (0..32)
	MAX-ACCESS read-only
	STATUS current
	DESCRIPTION
"ClkInputId is a unique identifier for all clock inputs/ sources."
	::= { inputPriorityListEntry 1 }

clkInputPriority OBJECT-TYPE
	SYNTAX INTEGER (0..15)
	MAX-ACCESS read-write
	STATUS current
	DESCRIPTION
	"ClkInputPriority indicates priority of reference clock 
	source. Highest priority is 0 and lowest 14. A priority
of 15 means that the port is disabled."
	::= { inputPriorityListEntry 2 }



clkInputListTable OBJECT-TYPE
	SYNTAX SEQUENCE OF ClkInputListEntry
	MAX-ACCESS not-accessible
	STATUS current
	DESCRIPTION
	"A table containing type (operation frequency), condition 
	(ok/not ok), status (enabled / disabled) and SSM info of 
	clock inputs.
	Default clkInputListTable for MCG1 is:
clkInputId	clkInputType	clkInputStatus	clkInput
Control	clkOutput
Control	SSMMonitorControl	SSM
bit	inputSSMValue
1	E1	ok	Enabled	Enabled	Disabled	Sa4	
2	E1	ok	Enabled	Enabled	Disabled	Sa4	
3	19,44MHz	ok	Enabled	Enabled	NA	NA	NA
4	19,44MHz	ok	Enabled	Enabled	NA	NA	NA
5	19,44MHz	fail	Enabled	Enabled	NA	NA	NA
6	19,44MHz	NA	Disabled	Disabled	NA	NA	NA
7	19,44MHz	NA	Disabled	Disabled	NA	NA	NA
8	19,44MHz	NA	Disabled	Disabled	NA	NA	NA
9	19,44MHz	NA	Disabled	Disabled	NA	NA	NA

	Default clkInputListTable for MCG2 is:

clkInputId	clkInputType	clkInputStatus	clkInput
Control	clkOutput
Control	SSMMonitorControl	SSM
bit	inputSSMValue
1	NA	NA	NA	NA	NA	NA	NA
2	NA	NA	NA	NA	NA	NA	NA
3	NA	NA	NA	NA	NA	NA	NA
4	NA	NA	NA	NA	NA	NA	NA
5	NA	NA	NA	NA	NA	NA	NA
6	NA	NA	NA	NA	NA	NA	NA
7	NA	NA	NA	NA	NA	NA	NA
8	NA	NA	NA	NA	NA	NA	NA
9	19,44MHz	ok	Enabled	Enabled	NA	NA	NA
"
	::= { clkInputs 2 }

forceRef OBJECT-TYPE
	SYNTAX INTEGER (0..32)
	MAX-ACCESS read-write
	STATUS current
	DESCRIPTION
"forceRef selects a clkInputId that will be forced as the active reference. 
Valid values are 1..9. Setting this value to 0 means forceRef is not active, 
therefore choosing the active reference is done according to priority table."
	::= { clkInputs 3 }

clkInputListEntry OBJECT-TYPE
	SYNTAX ClkInputListEntry
	MAX-ACCESS not-accessible
	STATUS current
	DESCRIPTION
		""
    INDEX  { clkInputId }
	::= { clkInputListTable 1 }

ClkInputListEntry ::= SEQUENCE {
	listEntryClkInputId		INTEGER,
	clkInputType	INTEGER,
	clkInputStatus	INTEGER,
	clkInputControl	INTEGER,
	ssmMonitorControl INTEGER,
	inputSSMValue	INTEGER,
	ssmSaBit          INTEGER,
	clkControllerMode      INTEGER,
	clkControllerFraming    INTEGER,
	clkControllerLineCoding INTEGER,     
	clkControllerImpedance E1CableImpedance,
	clkControllerLineLength T1CableLength
	
}

listEntryClkInputId OBJECT-TYPE
	SYNTAX INTEGER (0..32)
	MAX-ACCESS read-only
	STATUS current
	DESCRIPTION
	"ClkInputId is a unique identifier for all clock 
	inputs/sources. Local clock must have own clkInputId 
	identifier because it can be used as input for BITS 
	output."
	::= { clkInputListEntry 1 }

clkInputType OBJECT-TYPE
	SYNTAX INTEGER
	{
		freq8kHz      (1),
		freq1-544MHz  (2),
		freq-T1        (3),
		freq2-048MHz  (4),
		freq-E1        (5),
		freq19-44MHz  (6),
		freq-unknown  (255)
		
	}
	MAX-ACCESS read-only
	STATUS current
	DESCRIPTION
	"ClkInputType indentifies type (operation frequency) of
	clock input."
	::= { clkInputListEntry 2 }

clkInputStatus OBJECT-TYPE
	SYNTAX INTEGER
	{
		signalOk     (1),
		signalNotOk (2)
	}
	MAX-ACCESS read-only
	STATUS current
	DESCRIPTION
	"ClkInputStatus indentifies validity of clock input signal. 
	Signal is condisidered to be OK if it is present and valid. 
	Transition 	between two states will generate related trap."
	::= { clkInputListEntry 3 }

clkInputControl OBJECT-TYPE
	SYNTAX INTEGER
	{
		enabled  (1),
		disabled (2)
	}
	MAX-ACCESS read-write
	STATUS current
	DESCRIPTION
	"ClkInputControl indentifies activity (enabled / disabled) 
	of clock input. Disabling input will shutdown related
	receiver on HW level, If possible. There is some redundancy 
with clkInputPriority."
	::= { clkInputListEntry 4 }

ssmMonitorControl OBJECT-TYPE
	SYNTAX INTEGER
	{
		enabled  (1),
		disabled (2)
	}
	MAX-ACCESS read-write
	STATUS current
	DESCRIPTION
"SSMMonitorControl controls (enabled / disabled) SSM monitoring of EXT clock input. Enabling SSM monitor will initiate monitoring of the incoming SSM on the enabled reference. Enable is only allowed for EXT E1/T1 reference."
	::= { clkInputListEntry 5 }

inputSSMValue OBJECT-TYPE
	SYNTAX INTEGER
	{
		e1QualityUnknown 	(0),
		e1RecG811 		    (2),
		e1SSUA				(4),
		e1SSUB				(8),
		e1SETS				(11),
		e1DonotUsForSync	(15),
		t1G811 				  (32),
		t1G812TypeII 		(48),
		t1G812TypeIII 		(62),
		t1G812TypeIV 		(24),
		t1Stratum4			(20),
		t1813Option3 		(68),
		t1G812TypeV 		(30),
		t1SyncTraceUnknown 	(16),
		t1DoNoUseForSync    (12),
		t1Provisionable 	(6)

	}
	MAX-ACCESS read-only
	STATUS current
	DESCRIPTION
	"inputSSMValue identifies the actual SSM message read from 
	the incoming signal. Any change in the monitored SSM value
	will generate related trap if SSMMonitorControl is enabled"
	::= { clkInputListEntry 6 }


ssmSaBit OBJECT-TYPE
	SYNTAX INTEGER (4..8)
	MAX-ACCESS read-write
	STATUS current
	DESCRIPTION
"SSMSaBit selects which sa bit is used to transmit/receive SSM values. SSMSaBit is valid only in E1."
	::= { clkInputListEntry 8 }

clkControllerMode OBJECT-TYPE
	SYNTAX INTEGER
	{   
	 e1(1),
	 t1(2),
	 clk (3)
	}
	MAX-ACCESS read-write
	STATUS current
	DESCRIPTION
	"Controller modes:
	CLK - for 1.544M or 2.048M sine clock, relevant for CLK1 and CLK2
	E1, relevant for CLK3 and CLK4
	T1, relevant for CLK3 and CLK4
	If both CLK3 and CLK4 controllers are enabled, both must be configured to the same mode."
	::= { clkInputListEntry 9 }    

clkControllerFraming OBJECT-TYPE
	SYNTAX INTEGER
	{ 
	 undefined(0),   
	 unframed(1), 
	 t1SF(2),
	 t1ESF(3),
     e1NoCRC(4),
	 e1CRC (5)
	 
	}
	MAX-ACCESS read-write
	STATUS current
	DESCRIPTION
	"Sets the framing mode, according to controller type."    
	DEFVAL { unframed }
	::= { clkInputListEntry 10 }       

clkControllerLineCoding OBJECT-TYPE
	SYNTAX INTEGER
	{ 
	 undefined(0),  
	 ami(1), 
	 e1HDB3(2),
	 t1B8ZS(3)
	 	 
	}
	MAX-ACCESS read-write
	STATUS current
	DESCRIPTION
	"Sets the line coding for the TDM port 
	Avilable values:
		ami    - Alternate Mark Inversion 
		e1HDB3 - Hi Density Bipolar of order 3 only for E1
		t1B8ZS - Binary 8 with Zero Substitution for T1"    
		::= { clkInputListEntry 11 } 

clkControllerImpedance OBJECT-TYPE
	SYNTAX   E1CableImpedance
	MAX-ACCESS read-write
	STATUS current
	DESCRIPTION
	"Specifies the line termination impedance 
	value for the line so that the hardware can compensate for losses in signal strength.
	The valid options are 75 ohm and 120 ohm. 
	The cable-resistance command is valid only if controller mode is E1 or CLK."    
	::= { clkInputListEntry 12 }                 
	

clkControllerLineLength OBJECT-TYPE
	SYNTAX   T1CableLength
	MAX-ACCESS read-write
	STATUS current
	DESCRIPTION
	"Defines the length of the T1 line cable so that the hardware can compensate for losses
	 in signal strength."    
	::= { clkInputListEntry 13 } 





outputPriorityListTable OBJECT-TYPE
	SYNTAX SEQUENCE OF OutputPriorityListEntry
	MAX-ACCESS not-accessible
	STATUS current
	DESCRIPTION
	"A table containing the priority list related to EXT / BITS 
	output. Output priority list determines the source where 
	output signal is synchronized. Source may be either local 
	clock or any of the reference clock inputs. In relay mode 
	(reference input connected directly to BITS output) local 
	oscillator still follows the input priority list when 
	selecting reference clock. Object controls Select A
	in Figure A. Upon initialization this table is empty"
	::= { clkOutputs 1 }

outputPriorityListEntry OBJECT-TYPE
	SYNTAX OutputPriorityListEntry
	MAX-ACCESS not-accessible
	STATUS current
	DESCRIPTION
		""
    INDEX  { clkInputId }
	::= { outputPriorityListTable 1 }

OutputPriorityListEntry ::= SEQUENCE {
	outputClkInputId	INTEGER ,
	clkOutputPriority	INTEGER 
	}

outputClkInputId OBJECT-TYPE
	SYNTAX INTEGER (0..32)
	MAX-ACCESS read-only
	STATUS current
	DESCRIPTION
"ClkInputId is a unique identifier for all clock inputs/ sources.
EXT references are not valid IDs in this table."
	::= { outputPriorityListEntry 1 }

clkOutputPriority OBJECT-TYPE
	SYNTAX INTEGER (0..15)
	MAX-ACCESS read-write
	STATUS current
	DESCRIPTION
	"ClkOutputPriority indicates priority of reference clock 
	source. Highest priority is 0 and lowest 14. A priority
of 15 means that the port is disabled "
	::= { outputPriorityListEntry 2 }

extOutputSource OBJECT-TYPE
	SYNTAX INTEGER
	{
localClock    (1),-- PLL output used as source
relayThrough  (2)	-- outputPriorityList defines used source
	}
	MAX-ACCESS read-write
	STATUS current
	DESCRIPTION
"extOutputSource controls Select C in the figure above. 
It selects whether the EXT output will be derived based on 
-	localClock: clkOutput priority list (select A)
-	relayThrough: 
-	If relayThrough is selected then the values in 
clkOutput list are not applicable. The default value for 
this object is localClock."
	::= { clkOutputs 2 }



clkOutputListTable OBJECT-TYPE
	SYNTAX SEQUENCE OF ClkOutputListEntry
	MAX-ACCESS not-accessible
	STATUS current
	DESCRIPTION
	"A table containing type (operation frequency) and status 
	(disabled / enabled) of clock outputs.
	Default clkOutputListTable for MCG1 is:
clkOutputId	clkOutputType	clkOutputControl	SSMTxControl	outputSSMValue
1	E1	Enabled	Disabled	NA
2	E1	Enabled	Disabled	NA

Default clkOutputListTable for MCG2 is:
clkOutputId	clkOutputType	clkOutputControl	SSMTxControl	outputSSMValue
1	NA	NA	NA	NA
2	NA	NA	NA	NA
"
	::= { clkOutputs 3 }

clkOutputListEntry OBJECT-TYPE
	SYNTAX ClkOutputListEntry
	MAX-ACCESS not-accessible
	STATUS current
	DESCRIPTION
		""
    INDEX  { clkOutputId }
	::= { clkOutputListTable 1 }

ClkOutputListEntry ::= SEQUENCE {
	clkOutputId		INTEGER,
	clkOutputType	INTEGER,
	clkOutputControl INTEGER,
	ssmTxControl 	INTEGER,
	outputSSMValue	INTEGER
	}

clkOutputId OBJECT-TYPE
	SYNTAX INTEGER (0..32)
	MAX-ACCESS read-write
	STATUS current
	DESCRIPTION
	"ClkOutputId is a unique identifier for all clock outputs."
	::= { clkOutputListEntry 1 }

clkOutputType OBJECT-TYPE
	SYNTAX INTEGER
	{
		freq8kHz      (1),
		freq1-544MHz  (2),
		freqT1        (3),
		freq2-048MHz  (4),
		freqE1        (5),
		freq19-44MHz  (6),
		freq-unknown  (255)
	}
	MAX-ACCESS read-only
	STATUS current
	DESCRIPTION
	"ClkOutputType indentifies type (operation frequency) of
	clock output. The values in this object must comply with 
	the following restrictions:
For logical outputs 3, 4 & 5 the type must be 19.44Mhz. 
Fox EXT outputs, if also configured in clkInputType, the 
type must be the same"
	::= { clkOutputListEntry 2 }

clkOutputControl OBJECT-TYPE
	SYNTAX INTEGER
	{
		enabled  (1),
		disabled (2)
	}
	MAX-ACCESS read-write
	STATUS current
	DESCRIPTION
	"ClkOutputControl indentifies activity (enabled / disabled) 
	of clock output. Disabling output will shutdown related
	driver on HW level."
	::= { clkOutputListEntry 3 }


ssmTxControl OBJECT-TYPE
	SYNTAX INTEGER
	{
		enabled  (1),
		disabled (2)
	}
	MAX-ACCESS read-write
	STATUS current
	DESCRIPTION
	"SSMTxControl controls (enabled / disabled) SSM 
	transmission for EXT clock interface. Enabling SSM Tx will 
	initiate transmission of the synchronizaion status messages 
	out of the enabled reference. Enable is only allowed for 
	EXT E1/T1 reference."
	::= { clkOutputListEntry 4 }

outputSSMValue OBJECT-TYPE
	SYNTAX INTEGER
	{
		e1QualityUnknown 		(0),
		e1RecG811 			(2),
		e1SSUA				(4),
		e1SSUB				(8),
		e1SETS					(11),
		e1DonotUseForSync	(15),
		t1G811 				(32),
		t1G812TypeII 		(48),
		t1G812TypeIII 		(62),
		t1G812TypeIV 		(24),
		t1Stratum4			(20),
		t1G813Option3 		(68),
		t1G812TypeV 		(30),
		t1SyncTraceUnknown 	(16),
		t1DonotUseForSync	(12),
		t1Provisionable 	 (6)
	}
	MAX-ACCESS read-write
	STATUS current
	DESCRIPTION
	"outputSSMValue identifies the actual SSM message to be 
	sent out of the EXT intrerface."
	::= { clkOutputListEntry 5 }



clk3ToChildUpA OBJECT-TYPE
	SYNTAX TruthValue
	MAX-ACCESS read-write
	STATUS current
	DESCRIPTION
" Clk3ToChildUpA may be used for selecting clock reference for child-up-1a. It is valid only in MCG2. If the value is set to TRUE, CLK3A will be diverted to CHILD-UP-1A. If FALSE, CHILD-DOWN-1A is diverted. This flag practically controls mux #8 in Figure A."
	::= { clkOutputs 4 }

clk3ToChildUpB OBJECT-TYPE
	SYNTAX TruthValue
	MAX-ACCESS read-write
	STATUS current
	DESCRIPTION
" Clk3ToChildUpB may be used for selecting clock reference for child-up-1b. It is valid only in MCG2. If the value is set to TRUE, CLK3B will be diverted to CHILD-UP-1B. If FALSE, CHILD-DOWN-1B is diverted. This flag practically controls mux #9 in Figure A."
	::= { clkOutputs 5 }



entityUp NOTIFICATION-TYPE
	OBJECTS { shelfId, slotId }
	STATUS current
	DESCRIPTION
	"A entityUp notification signifies that the sending 
	protocol entity is powered up, has been initialized, is 
	fully operational and is ready to serve any requests."
	::= { clkMgrAlarms 1 }

pllOperationModeChange NOTIFICATION-TYPE
	OBJECTS { shelfId, slotId, pllOperationMode }
	STATUS current
	DESCRIPTION
	"A pllOperationModeChange notification signifies that the 
	sending protocol entity's local oscillator has new 
	operation mode. Operation mode (synchronized, hold-over, 
	free-run) indicates operation mode of MCG's internal 
	oscillator."
	::= { clkMgrAlarms 2 }

pllHoldOverAlarm NOTIFICATION-TYPE
	OBJECTS { shelfId, slotId }
	STATUS current
	DESCRIPTION
	"A pllHoldOverAlarm notification signifies that the sending 
	protocol entity's local clock has been on hold-over 
operation mode more than 15 seconds. After this alarm is set, the outgoing SSM values which have been enabled in the outgoing direction are set to Stratum 3 value"
	::= { clkMgrAlarms 3 }

clkInputDown NOTIFICATION-TYPE
	OBJECTS { shelfId, slotId, clkInputId }
	STATUS current
	DESCRIPTION
	"A clkInputDown notification signifies that the sending 
	protocol entity recognizes that signal on clock input has 
	been lost."
	::= { clkMgrAlarms 4 }

clkInputUp NOTIFICATION-TYPE
	OBJECTS { shelfId, slotId, clkInputId }
	STATUS current
	DESCRIPTION
	"A clkInputUp notification signifies that the sending 
	protocol entity recognizes that signal on clock input has 
	been recovered."
	::= { clkMgrAlarms 5 }

hardwareError NOTIFICATION-TYPE
	OBJECTS { shelfId, slotId, errorType}
	STATUS current
	DESCRIPTION
	"A hardwareError notification signifies that the sending 
	protocol entity recognizes HW related error. Possible 
	errors: system clock not oscillating, external 
	synchronization / BITS output LOS (MCG1 only), MCG1 
	frequency out of range (MCG2 only), main MCG frequency 
	out of range (redundant MCGs only)."
	::= { clkMgrAlarms 6 }

mcgOperationModeChange NOTIFICATION-TYPE
	OBJECTS { shelfId, slotId, mcgOperationMode }
	STATUS current
	DESCRIPTION
	"A mcgOperationModeChange notification signifies that the 
	sending protocol entity has new operational status. 
	Operational status of entity may be: main (active), 
	redundant (passive), test (used for testing, sending clock 
	signals is restricted) or separate (unit is not in use, 
	sending clock signals is prohibited)."
	::= { clkMgrAlarms 7 }

extInputSSMChanged NOTIFICATION-TYPE
	OBJECTS { shelfId, slotId, clkInputId, inputSSMValue }
	STATUS current
	DESCRIPTION
	"A extInputSSMChanged notification signifies that the 
	sending protocol entity recognizes that SSM value on it's 
	EXT input has changed. Have contain new EXT input id and 
	new SSM value as attributes."
	::= { clkMgrAlarms 8 }

      
END
